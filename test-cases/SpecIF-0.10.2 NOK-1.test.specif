# SpecIF-0.10.2 NOK-1
Schema-defects:
- dataType[0] 'type' missing
- dataType[2] 'min' missing - permissible, because it is optional.
- Rights: Creative Commons 4.0 CC BY-SA, https://creativecommons.org/licenses/by-sa/4.0/

## Project Information (SpecIF:Heading)
- dcterms:description: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
  This specification method integrates and represents:
  - processes, system composition and requirements (dynamic, static and detail views)
  - mechanic, electric and software components with their interfaces.
  It is important to understand, that all plans (diagrams) are views of a common system engineering model, sometimes called 'system repository'. Thus, consistency is always maintained.
  The model elements are connected with relations, most of which are defined by positioning graph elements. For example, if a system component is drawn within another, a relationship 'contains' is created in the logic representation of the engineering model. Other relations, such as a system component 'complies-with' a requirement are created manually.
  Also, the documents are generated from the system engineering model. The ordering is in most projects (it can be rearranged, however, if appropriate):
  - All plans
  - A glossary with descriptions of all model elements appearing on one or more plans
  - A hierarchically ordered list of requirements
  - A list of open issues.
  Please note that plans list related model elements and model elements list related requirements .. and vice versa. Active hyper-links are used, so that it is easy to jump between related model elements.
  Stakeholders:
  | Name | Organisation | Telephone | Email |
  | --- | --- | --- | --- |
  | Vorname Nachname | Hersteller AG |  |  |
  Legend:
  To distinguish their type, element names are preceded by one of the following symbols:
  | ▣ | Plan | A 'Diagram' is a graphical model view with a specific communication purpose, e.g. a business process or system composition. |
  | --- | --- | --- |
  | ■ | Actor (Role, Function) | An 'Actor' is a fundamental model element type representing an active entity, be it an activity, a process step, a function, a system component or a role. |
  | ● | State (Information) | A 'State' is a fundamental model element type representing a passive entity, be it a value, a condition, an information storage or even a physical shape. |
  | ♦ | Event | An 'Event' is a fundamental model element type representing a time reference, a change in condition/value or more generally a synchronisation primitive. |
  | ✶ | Feature | A 'Feature' is an intentional distinguishing characteristic of a system, often a unique selling proposition. |
  | ↯ | Requirement | A 'Requirement' is a singular documented physical and functional need that a particular design, product or process must be able to perform. |

## System Composition (SpecIF:Heading)
- dcterms:description: .. showing the system and its composition of modules (at a higher level) and components (at a lower level). The relevant interfaces between the disciplines mechanical, electrical and software engineering are shown.

## Scenarios (SpecIF:Heading)
- dcterms:description: .. showing the behavioral aspects of system design, both from external user perspective ('black box') and from internal perspective ('white box').

## Dimming (SpecIF:Heading)

## SmartHome System (SpecIF:Diagram)
- dcterms:description: The Smart-Home-System consists of sensors on the left side, the controller in the middle and the actuators on the right side.
  Model View:
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- SpecIF:Notation: FMC Block Diagram
- Status: 10_initial

## User Activity (SpecIF:Diagram)
- dcterms:description: This shows the defined sequences of manual operation to activate the device.
  Model View:
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- SpecIF:Notation: BPMN Process Model
- Status: 20_drafted

## Bulb (FMC:Actor)
- dcterms:description: Dimmable candescent light-bulb 230V.

## down (FMC:State)
- dcterms:description: The button to drive down the dimmer, shading or similar devices.

## Parts List (SpecIF:Heading)
- dcterms:description: This Parts List has been automatically generated from the model.

## Statements
- SmartHome System SpecIF:shows Bulb
- SmartHome System SpecIF:shows down
