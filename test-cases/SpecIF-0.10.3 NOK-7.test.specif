# Test (schema 0-10-3) NOK-7
resources[0].properties[2]: property value is not a boolean.
- Rights: Creative Commons 4.0 CC BY-SA, https://creativecommons.org/licenses/by-sa/4.0/

## Project Information (SpecIF:Heading)
- dcterms:description: The next property value '1' is invalid
- Boolean Test: 1
