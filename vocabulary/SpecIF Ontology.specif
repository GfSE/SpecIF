# SpecIF Ontology
The SpecIF ontology collects terms used in the domain of systems engineering and requirements management. Agreed-upon terms help both collaborators to communicate more clearly and systems to match data fields automatically.
- Rights: Creative Commons 4.0 CC BY-SA, https://creativecommons.org/licenses/by-sa/4.0/

## SpecIF Ontology (dcterms:title)
- dcterms:type: W3C:Ontology

## Introduction (dcterms:title)
- dcterms:description: The SpecIF Ontology (Vocabulary) collects terms used in the domain of systems engineering and requirements management. Agreed-upon terms help both collaborators to communicate more clearly and systems to match data fields automatically. SpecIF adopts terms and their definitions from other initiatives, for example from the Dublin Core Metadata Initiative (DCMI), the Open Services for Lifecycle Collaboration (OSLC) and the International Requirements Engineering Board (IREB). The ProSTEP iViP association has also defined a set of attribute names to be used in ReqIF data, but those are not freely available and cannot be referenced here.
  All terms carry a namespace, which is the first part separated with ':' or '.' ― they are thus easily recognized in text and data fields. For display, systems may choose to replace SpecIF terms by domain or language specific words. This collection itself is structured according to SpecIF using it's vocabulary. Hence, the titles are recognized as such, because they are tagged with '[[dcterms:title]]', whereas paragraphs like this one are tagged with '[[dcterms:description]]'.
  The terms have a lifecycle status as follows:
  - experimental: The term is being used in first projects, but has not yet any normative maturity.
  - submitted: The term has been submitted for adoption.
  - released: The term has been adopted for use with SpecIF and is preferred among equivalent terms.
  - equivalent: The term has been adopted for use with SpecIF, but the released term is preferred.
  - deprecated: The term shall not any more be used with SpecIF; use the released term.
  The Specification Interchange Facility (SpecIF) is the result of an initiative by the Gesellschaft für Systems Engineering (GfSE), the German chapter of The International Council on Systems Engineering (INCOSE).
  All information provided here is made available according to Creative Commons 4.0 CC BY-SA or the license chosen by the respective publishers. We appreciate any contribution or proposal; please contact Dr. Oskar von Dungern.
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
## Namespaces (dcterms:title)
- dcterms:description: A 'Namespace' is a is a set of signs (names) that are used to identify and refer to objects of various kinds. A namespace ensures that all of a given set of objects have unique names so that they can be easily identified. (Source: Wikipedia)

## W3C: (SpecIF:Namespace)
- dcterms:description: The World Wide Web Consortium (W3C) is the main international standards organization for the World Wide Web. Founded in 1994 and led by Tim Berners-Lee, the consortium is made up of member organizations that maintain full-time staff working together in the development of standards for the World Wide Web. W3C also engages in education and outreach, develops software and serves as an open forum for discussion about the Web. *(Source: [Wikipedia](https://en.wikipedia.org/wiki/World_Wide_Web_Consortium))*
- SpecIF:Origin: https://www.w3.org/standards/semanticweb

## xs: (SpecIF:Namespace)
- SpecIF:Origin: http://www.w3.org/2001/XMLSchema#

## xsd: (SpecIF:Namespace)
- SpecIF:Origin: http://www.w3.org/2001/XMLSchema#

## owl: (SpecIF:Namespace)
- SpecIF:Origin: http://www.w3.org/2002/07/owl#

## dcterms: (SpecIF:Namespace)
- SpecIF:Origin: http://purl.org/dc/terms/

## schema: (SpecIF:Namespace)
- dcterms:description: Schema.org is a collaborative, community activity with a mission to create, maintain, and promote schemas for structured data on the Internet, on web pages, in email messages, and beyond.
- SpecIF:Origin: https://schema.org/

## rdf: (SpecIF:Namespace)
- SpecIF:Origin: http://www.w3.org/1999/02/22-rdf-syntax-ns#

## rdfs: (SpecIF:Namespace)
- SpecIF:Origin: http://www.w3.org/2000/01/rdf-schema#

## foaf: (SpecIF:Namespace)
- SpecIF:Origin: http://xmlns.com/foaf/0.1/

## FMC: (SpecIF:Namespace)
- dcterms:description: FMC is the acronym for "Fundamental Modeling Concepts", primarily a consistent and coherent way to think and talk about dynamic systems. It enables people to communicate the concepts and structures of complex informational systems in an efficient way among the different types of stakeholders. *(Source: [What is FMC?](http://www.fmc-modeling.org/quick-intro))*
- SpecIF:Origin: http://fmc-modeling.org

## IR: (SpecIF:Namespace)
- dcterms:description: Interaction Room Workshop Method
- SpecIF:Origin: https://www.adesso.de/de/impulse/interaction-room/index.jsp

## IREB: (SpecIF:Namespace)
- SpecIF:Origin: https://www.ireb.org/de/cpre/glossary/, https://www.ireb.org/en/downloads/#cpre-glossary

## ReqIF. (SpecIF:Namespace)
- SpecIF:Origin: https://www.prostep.org/fileadmin/downloads/PSI_ImplementationGuide_ReqIF_V1-7.pdf

## ReqIF-WF. (SpecIF:Namespace)
- SpecIF:Origin: https://www.prostep.org/fileadmin/downloads/Recommendation_ReqIF_V2_RZ3.pdf

## HIS: (SpecIF:Namespace)
- SpecIF:Origin: https://www.itwissen.info/Herstellerinitiative-Software-Automotive-HIS.html

## oslc: (SpecIF:Namespace)
- SpecIF:Origin: http://open-services.net/ns/core#

## oslc_rm: (SpecIF:Namespace)
- SpecIF:Origin: http://open-services.net/ns/rm#

## ArchiMate: (SpecIF:Namespace)
- dcterms:description: ArchiMate is an open and independent enterprise architecture modeling language to support the description, analysis and visualization of architecture within and across business domains[1] in an unambiguous way.  ArchiMate is a technical standard from The Open Group and is based on concepts from the now superseded IEEE 1471 standard. It is supported by various tool vendors and consulting firms. ArchiMate is also a registered trademark of The Open Group. The Open Group has a certification program for ArchiMate users, software tools and courses.  *(Source: [Wikipedia](https://en.wikipedia.org/wiki/ArchiMate))*
- SpecIF:Origin: https://pubs.opengroup.org

## bpmn: (SpecIF:Namespace)
- SpecIF:Origin: https://www.bpmn.org/

## UML: (SpecIF:Namespace)
- SpecIF:Origin: https://www.omg.org/spec/UML

## SysML: (SpecIF:Namespace)
- SpecIF:Origin: https://www.omg.org/spec/SysML

## SpecIF: (SpecIF:Namespace)
- SpecIF:Origin: https://specif.de

## DDP: (SpecIF:Namespace)
- dcterms:description: Digital Data Package defined by prostep IVIP.
- SpecIF:Origin: https://www.prostep.org/projekte/digital-data-package-ddp

## Resource Class Terms (dcterms:title)
- dcterms:description: A resource represents an artefact, e.g. a model element or a requirement. The terms listed in this chapter may be used to distinguish different classes (types) of artefacts constituting a system specification. A resource may serve as subject or as object in a subject-predicate-object statement. Each resource class may define an individual set of properties for carrying the information 'payload'.
  A resource class corresponds to a 'SPEC-OBJECT-TYPE' and a resource is a 'SPEC-OBJECT' in the Requirements Interchange Format (ReqIF). In ArchiMate® 3.0, a resource is an Element.

## SpecIF:Paragraph (SpecIF:TermResourceClass)
- dcterms:identifier: RC-Paragraph
- SpecIF:Revision: 1.1
- dcterms:description: A 'Paragraph' is an unspecified information in a document at any level.
- SpecIF:Domain: Base, Requirement Engineering, Automotive Stakeholder Request Clarification Process, System Model Integration
- SpecIF:LifecycleStatus: SpecIF:LifecycleStatusReleased
- SpecIF:LocalTerm: Paragraph
- SpecIF:LocalTermPlural: Paragraphs
- SpecIF:isHeading: false
- SpecIF:Instantiation: auto, user

## SpecIF:Information (SpecIF:TermResourceClass)
- dcterms:description: A 'Paragraph' is an unspecified information in a document at any level.
- SpecIF:Domain: Base
- SpecIF:LifecycleStatus: SpecIF:LifecycleStatusEquivalent
- SpecIF:LocalTerm: Information
- SpecIF:LocalTermPlural: Informations
- SpecIF:isHeading: false
- SpecIF:Instantiation: auto, user

## SpecIF:Heading (SpecIF:TermResourceClass)
- dcterms:identifier: RC-Folder
- SpecIF:Revision: 1.1
- dcterms:description: A 'Heading' is a chapter title at any level with optional description.
- SpecIF:Domain: Base, Requirement Engineering, Automotive Stakeholder Request Clarification Process, System Model Integration
- SpecIF:LifecycleStatus: SpecIF:LifecycleStatusReleased
- SpecIF:LocalTerm: Heading, Chapter Title
- SpecIF:LocalTermPlural: Headings
- SpecIF:isHeading: true
- SpecIF:Instantiation: auto, user

## SpecIF:Folder (SpecIF:TermResourceClass)
- dcterms:description: A 'Folder' may appear at any level with optional description.
- SpecIF:Domain: Base
- SpecIF:LifecycleStatus: SpecIF:LifecycleStatusDeprecated
- SpecIF:LocalTerm: Folder
- SpecIF:LocalTermPlural: Folders
- SpecIF:isHeading: true
- SpecIF:Instantiation: auto, user

## SpecIF:View (SpecIF:TermResourceClass)
- SpecIF:Revision: 1.2
- dcterms:description: A 'Model Diagram' is a graphical model view with a specific communication purpose, e.g. a business process or system composition.
- SpecIF:Domain: System Model Integration
- SpecIF:LifecycleStatus: SpecIF:LifecycleStatusReleased
- SpecIF:LocalTerm: Model Diagram, Diagram, Plan
- SpecIF:Icon: ▣
- SpecIF:isHeading: false
- SpecIF:Instantiation: auto

## SpecIF:Views (SpecIF:TermResourceClass)
- SpecIF:Revision: 1.2
- SpecIF:Domain: System Model Integration
- SpecIF:LifecycleStatus: SpecIF:LifecycleStatusReleased
- SpecIF:LocalTerm: Model Diagrams, Diagrams, Plans
- SpecIF:Icon: ▣
- SpecIF:isHeading: false
- SpecIF:Instantiation: auto

## ArchiMate:Viewpoint (SpecIF:TermResourceClass)
- SpecIF:Revision: 1.2
- SpecIF:LocalTerm: Model Diagram
- SpecIF:LocalTermPlural: Model Diagrams
- dcterms:description: A viewpoint in the ArchiMate language is a selection of a relevant subset of the ArchiMate elements and their relationships. This is the representation of that part of an architecture that is expressed in different diagrams.
- SpecIF:Domain: System Model Integration
- SpecIF:LifecycleStatus: SpecIF:LifecycleStatusEquivalent
- SpecIF:Icon: ▣
- SpecIF:isHeading: false
- SpecIF:Instantiation: auto

## SpecIF:Diagram (SpecIF:TermResourceClass)
- dcterms:description: A 'Diagram' is a graphical model view with a specific communication purpose, e.g. a business process or system composition.
- SpecIF:Domain: System Model Integration
- SpecIF:LifecycleStatus: SpecIF:LifecycleStatusDeprecated
- SpecIF:LocalTerm: Model Diagram
- SpecIF:LocalTermPlural: Model Diagrams
- SpecIF:isHeading: false

## IREB:Requirement (SpecIF:TermResourceClass)
- dcterms:identifier: RC-Requirement
- SpecIF:Revision: 1.2
- dcterms:description: A 'Requirement' is a singular documented physical and functional need that a particular design, product or process must be able to perform. (source: Wikipedia)
  Definition:
  1. A condition or capability needed by a user to solve a problem or achieve an objective.
  2. A condition or capability that must be met or possessed by a system or system component to satisfy a contract, standard, specification, or other formally imposed documents.
  3. A documented representation of a condition or capability as in (1) or (2).
  Note: The definition above is the classic one from IEEE Std 610.12 of 1990. Alternatively, we also give a more modern definition:
  1. A need perceived by a stakeholder.
  2. A capability or property that a system shall have.
  3. A documented representation of a need, capability or property.
- SpecIF:LocalTerm: Requirement
- SpecIF:LocalTermPlural: Requirements
- SpecIF:Domain: Requirement Engineering
- SpecIF:LifecycleStatus: SpecIF:LifecycleStatusReleased
- SpecIF:Icon: ↯
- SpecIF:isHeading: false
- SpecIF:Instantiation: user

## SpecIF:Requirement (SpecIF:TermResourceClass)
- dcterms:identifier: RC-Requirement
- dcterms:description: A 'Requirement' is a singular documented physical and functional need that a particular design, product or process must be able to perform. (source: Wikipedia)
  Definition:
  1. A condition or capability needed by a user to solve a problem or achieve an objective.
  2. A condition or capability that must be met or possessed by a system or system component to satisfy a contract, standard, specification, or other formally imposed documents.
  3. A documented representation of a condition or capability as in (1) or (2).
  Note: The definition above is the classic one from IEEE Std 610.12 of 1990. Alternatively, we also give a more modern definition:
  1. A need perceived by a stakeholder.
  2. A capability or property that a system shall have.
  3. A documented representation of a need, capability or property.
- SpecIF:Domain: Requirement Engineering
- SpecIF:LifecycleStatus: SpecIF:LifecycleStatusDeprecated
- SpecIF:LocalTerm: Requirement
- SpecIF:LocalTermPlural: Requirements
- SpecIF:Icon: ❢
- SpecIF:isHeading: false
- SpecIF:Instantiation: user

## ReqIF-WF.Requirement (SpecIF:TermResourceClass)
- SpecIF:Revision: 1.2
- dcterms:description: A 'Requirement' is a singular documented physical and functional need that a particular design, product or process must be able to perform. (source: Wikipedia)
  Definition:
  1. A condition or capability needed by a user to solve a problem or achieve an objective.
  2. A condition or capability that must be met or possessed by a system or system component to satisfy a contract, standard, specification, or other formally imposed documents.
  3. A documented representation of a condition or capability as in (1) or (2).
  Note: The definition above is the classic one from IEEE Std 610.12 of 1990. Alternatively, we also give a more modern definition:
  1. A need perceived by a stakeholder.
  2. A capability or property that a system shall have.
  3. A documented representation of a need, capability or property.
- SpecIF:Domain: Automotive Stakeholder Request Clarification Process
- SpecIF:LifecycleStatus: SpecIF:LifecycleStatusReleased
- SpecIF:LocalTerm: Requirement
- SpecIF:LocalTermPlural: Requirements
- SpecIF:Icon: ❢
- SpecIF:isHeading: false
- SpecIF:Instantiation: user

## SpecIF:Namespace (SpecIF:TermResourceClass)
- SpecIF:Revision: 1.2
- SpecIF:Domain: Ontology
- SpecIF:LifecycleStatus: SpecIF:LifecycleStatusReleased
- SpecIF:LocalTerm: Namespace
- SpecIF:LocalTermPlural: Namespaces
- SpecIF:isHeading: false
- SpecIF:Instantiation: user

## SpecIF:Resource (SpecIF:TermResourceClass)
- SpecIF:Domain: System Model Integration
- SpecIF:LifecycleStatus: SpecIF:LifecycleStatusSubmitted
- SpecIF:LocalTerm: Resource
- SpecIF:LocalTermPlural: Resources
- SpecIF:isHeading: false
- SpecIF:Instantiation: auto

## SpecIF:Statement (SpecIF:TermResourceClass)
- SpecIF:Domain: System Model Integration
- SpecIF:LifecycleStatus: SpecIF:LifecycleStatusSubmitted
- SpecIF:LocalTerm: Statement
- SpecIF:LocalTermPlural: Statements
- SpecIF:isHeading: false
- SpecIF:Instantiation: auto

## SpecIF:Property (SpecIF:TermResourceClass)
- SpecIF:Domain: System Model Integration
- SpecIF:LifecycleStatus: SpecIF:LifecycleStatusSubmitted
- SpecIF:LocalTerm: Property
- SpecIF:LocalTermPlural: Properties
- SpecIF:isHeading: false
- SpecIF:Instantiation: auto

## FMC:Plan (SpecIF:TermResourceClass)
- dcterms:description: A 'Plan' is a graphical model view with a specific communication purpose, e.g. a business process or system composition.
- SpecIF:LifecycleStatus: SpecIF:LifecycleStatusEquivalent
- SpecIF:LocalTerm: Plan
- SpecIF:LocalTermPlural: Plans
- SpecIF:isHeading: false

## SpecIF:ModelElement (SpecIF:TermResourceClass)
- SpecIF:Revision: 1.2
- dcterms:description: Is a generalized type for model elements.
- SpecIF:Domain: System Model Integration
- SpecIF:LifecycleStatus: SpecIF:LifecycleStatusReleased
- SpecIF:LocalTerm: Model Element
- SpecIF:LocalTermPlural: Model Elements
- SpecIF:isHeading: false
- SpecIF:Instantiation: auto

## FMC:Actor (SpecIF:TermResourceClass)
- dcterms:identifier: RC-Actor
- SpecIF:Revision: 1.2
- dcterms:description: An 'Actor' is a fundamental model element type representing an active entity, be it an activity, a process step, a function, a system component or a role.
  The particular use of FMC:Actor is specified with a [[dcterms:type]] property. The values of that property can be ontology-terms, such as [[bpmn:timer]].
- SpecIF:Domain: System Model Integration
- SpecIF:LifecycleStatus: SpecIF:LifecycleStatusReleased
- SpecIF:LocalTerm: Actor
- SpecIF:LocalTermPlural: Actors
- SpecIF:Icon: ■
- SpecIF:isHeading: false
- SpecIF:Instantiation: auto

## FMC:State (SpecIF:TermResourceClass)
- dcterms:identifier: RC-State
- SpecIF:Revision: 1.2
- dcterms:description: A 'State' is a fundamental model element type representing a passive entity, be it a value, a condition, an information storage or even a physical shape.
- SpecIF:Domain: System Model Integration
- SpecIF:LifecycleStatus: SpecIF:LifecycleStatusReleased
- SpecIF:LocalTerm: State
- SpecIF:LocalTermPlural: States
- SpecIF:Icon: ●
- SpecIF:isHeading: false
- SpecIF:Instantiation: auto

## FMC:Event (SpecIF:TermResourceClass)
- dcterms:identifier: RC-Event
- SpecIF:Revision: 1.2
- dcterms:description: An 'Event' is a fundamental model element type representing a time reference, a change in condition/value or more generally a synchronization primitive.
- SpecIF:Domain: System Model Integration
- SpecIF:LifecycleStatus: SpecIF:LifecycleStatusReleased
- SpecIF:LocalTerm: Event
- SpecIF:LocalTermPlural: Events
- SpecIF:Icon: ⬧
- SpecIF:isHeading: false
- SpecIF:Instantiation: auto

## SpecIF:Collection (SpecIF:TermResourceClass)
- dcterms:identifier: RC-Collection
- SpecIF:Revision: 1.2
- SpecIF:LocalTerm: Collection or Group
- SpecIF:LocalTermPlural: Collections and Groups
- dcterms:description: A 'Collection' is a logic (often conceptual) group of resources linked with a [[SpecIF:contains]] statement. It corresponds to a 'Group' in BPMN Diagrams.
  BPMN: An arbitrary set of objects can be defined as a Group to show that they logically belong together. (source: BPMN Tutorial)
- SpecIF:Domain: System Model Integration
- SpecIF:LifecycleStatus: SpecIF:LifecycleStatusReleased
- SpecIF:Icon: ⬚
- SpecIF:isHeading: false
- SpecIF:Instantiation: auto

## bpmn:group (SpecIF:TermResourceClass)
- dcterms:description: BPMN: An arbitrary set of objects can be defined as a Group to show that they logically belong together. Like all BPMN 'artifacts', a group does not influence execution semantics. In PBMN, a group can be freely applied, even across pool boundaries. (source: BPMN Reference)
- SpecIF:LifecycleStatus: SpecIF:LifecycleStatusExperimental

## SpecIF:Comment (SpecIF:TermResourceClass)
- dcterms:identifier: RC-Comment
- SpecIF:Revision: 1.1
- dcterms:description: A 'Comment' is reader feedback referring to a model element ('resource' or 'statement' in general).
- SpecIF:Domain: Base
- SpecIF:LifecycleStatus: SpecIF:LifecycleStatusReleased
- SpecIF:LocalTerm: Comment
- SpecIF:LocalTermPlural: Comments
- SpecIF:Icon: 🗅
- SpecIF:isHeading: false
- SpecIF:Instantiation: auto

## SpecIF:Note (SpecIF:TermResourceClass)
- dcterms:identifier: RC-Note
- SpecIF:Revision: 1.1
- dcterms:description: A 'Note' is additional information by the author referring to any resource.
- SpecIF:LifecycleStatus: SpecIF:LifecycleStatusReleased
- SpecIF:LocalTerm: Note
- SpecIF:LocalTermPlural: Notes
- SpecIF:isHeading: false
- SpecIF:Instantiation: user

## SpecIF:Vote (SpecIF:TermResourceClass)
- dcterms:identifier: RC-Vote
- SpecIF:Revision: 1.2
- dcterms:description: A 'Vote' is an opinion referring to any resource or statement.
- SpecIF:LifecycleStatus: SpecIF:LifecycleStatusReleased
- SpecIF:LocalTerm: Vote
- SpecIF:LocalTermPlural: Votes
- SpecIF:isHeading: false
- SpecIF:Instantiation: user

## IR:Annotation (SpecIF:TermResourceClass)
- dcterms:description: An Interaction-Room 'Annotation' indicates a point of special interest. Examples are customer or user value, product features with prominent benefit,effort or challenges during development.
- SpecIF:LifecycleStatus: SpecIF:LifecycleStatusReleased
- SpecIF:LocalTerm: Annotation
- SpecIF:LocalTermPlural: Annotations
- SpecIF:LocalTermPlural: Annotations
- SpecIF:Icon: ►
- SpecIF:isHeading: false
- SpecIF:Instantiation: user

## SpecIF:Issue (SpecIF:TermResourceClass)
- dcterms:description: An 'Issue' is a question to answer or decision to take which is worth tracking.
- SpecIF:Domain: Issue Management
- SpecIF:LifecycleStatus: SpecIF:LifecycleStatusReleased
- SpecIF:LocalTerm: Open Issue
- SpecIF:LocalTermPlural: Open Issues
- SpecIF:isHeading: false

## SpecIF:Permissions (SpecIF:TermResourceClass)
- SpecIF:Revision: 1.2
- dcterms:description: Permissions are a set of user rights, each allowing to use a certain function and/or to access a certain data set.
- SpecIF:Domain: System Model Integration
- SpecIF:LifecycleStatus: SpecIF:LifecycleStatusReleased
- SpecIF:LocalTerm: Permission
- SpecIF:LocalTermPlural: Permissions
- SpecIF:isHeading: false
- SpecIF:Instantiation: user

## SpecIF:OntologyTerm (SpecIF:TermResourceClass)
- SpecIF:Revision: 1.2
- SpecIF:Domain: Ontology
- SpecIF:LifecycleStatus: SpecIF:LifecycleStatusReleased
- SpecIF:LocalTerm: Term
- SpecIF:LocalTermPlural: Terms
- SpecIF:isHeading: false

## SpecIF:TermResourceClass (SpecIF:TermResourceClass)
- SpecIF:Revision: 1.2
- dcterms:description: A term for SpecIF resources, often used as title of a resourceClass to denote the class type.
- SpecIF:Domain: Ontology
- SpecIF:LifecycleStatus: SpecIF:LifecycleStatusReleased
- SpecIF:LocalTerm: Ressource
- SpecIF:LocalTermPlural: Ressources
- SpecIF:isHeading: false
- SpecIF:Instantiation: user

## SpecIF:TermStatementClass (SpecIF:TermResourceClass)
- SpecIF:Revision: 1.2
- dcterms:description: A term for SpecIF statements, often used as title of a statementClass to denote the class type.
- SpecIF:Domain: Ontology
- SpecIF:LifecycleStatus: SpecIF:LifecycleStatusReleased
- SpecIF:LocalTerm: Statement
- SpecIF:LocalTermPlural: Statements
- SpecIF:isHeading: false
- SpecIF:Instantiation: user

## SpecIF:TermPropertyClass (SpecIF:TermResourceClass)
- SpecIF:Revision: 1.2
- dcterms:description: A term for SpecIF properties, often used as title of a propertyClass to denote the class type.
- SpecIF:Domain: Ontology
- SpecIF:LifecycleStatus: SpecIF:LifecycleStatusReleased
- SpecIF:LocalTerm: Property
- SpecIF:LocalTermPlural: Properties
- SpecIF:isHeading: false

## SpecIF:TermPropertyClassString (SpecIF:TermResourceClass)
- SpecIF:Revision: 1.2
- dcterms:description: A term for SpecIF properties with data type 'xs:string', often used as title of a propertyClass to denote the class type.
- SpecIF:Domain: Ontology
- SpecIF:LifecycleStatus: SpecIF:LifecycleStatusReleased
- SpecIF:LocalTerm: Property (Text)
- SpecIF:LocalTermPlural: Properties (Text)
- SpecIF:isHeading: false
- SpecIF:Instantiation: user

## SpecIF:TermPropertyClassBoolean (SpecIF:TermResourceClass)
- SpecIF:Revision: 1.2
- dcterms:description: A term for SpecIF properties with data type 'xs:boolean', often used as title of a propertyClass to denote the class type.
- SpecIF:Domain: Ontology
- SpecIF:LifecycleStatus: SpecIF:LifecycleStatusReleased
- SpecIF:LocalTerm: Property (Boolean)
- SpecIF:LocalTermPlural: Properties (Boolean)
- SpecIF:isHeading: false
- SpecIF:Instantiation: user

## SpecIF:TermPropertyClassInteger (SpecIF:TermResourceClass)
- SpecIF:Revision: 1.2
- dcterms:description: A term for SpecIF properties with data type 'xs:integer', often used as title of a propertyClass to denote the class type.
- SpecIF:Domain: Ontology
- SpecIF:LifecycleStatus: SpecIF:LifecycleStatusReleased
- SpecIF:LocalTerm: Property (Integer)
- SpecIF:LocalTermPlural: Properties (Integer)
- SpecIF:isHeading: false
- SpecIF:Instantiation: user

## SpecIF:TermPropertyClassReal (SpecIF:TermResourceClass)
- SpecIF:Revision: 1.2
- dcterms:description: A term for SpecIF properties with data type 'xs:double', often used as title of a propertyClass to denote the class type.
- SpecIF:Domain: Ontology
- SpecIF:LifecycleStatus: SpecIF:LifecycleStatusReleased
- SpecIF:LocalTerm: Property (Real)
- SpecIF:LocalTermPlural: Properties (Real)
- SpecIF:isHeading: false
- SpecIF:Instantiation: user

## SpecIF:TermPropertyClassTimestamp (SpecIF:TermResourceClass)
- SpecIF:Revision: 1.2
- dcterms:description: A term for SpecIF properties with data type 'xs:dateTime', often used as title of a propertyClass to denote the class type.
- SpecIF:Domain: Ontology
- SpecIF:LifecycleStatus: SpecIF:LifecycleStatusReleased
- SpecIF:LocalTerm: Property (Timestamp)
- SpecIF:LocalTermPlural: Properties (Timestamp)
- SpecIF:isHeading: false
- SpecIF:Instantiation: user

## SpecIF:TermPropertyClassDuration (SpecIF:TermResourceClass)
- SpecIF:Revision: 1.2
- dcterms:description: A term for SpecIF properties with data type 'xs:duration', often used as title of a propertyClass to denote the class type.
- SpecIF:Domain: Ontology
- SpecIF:LifecycleStatus: SpecIF:LifecycleStatusReleased
- SpecIF:LocalTerm: Property (Duration)
- SpecIF:LocalTermPlural: Properties (Duration)
- SpecIF:isHeading: false
- SpecIF:Instantiation: user

## SpecIF:TermPropertyClassURI (SpecIF:TermResourceClass)
- SpecIF:Revision: 1.2
- dcterms:description: A term for SpecIF properties with data type 'xs:anyURI', often used as title of a propertyClass to denote the class type.
- SpecIF:Domain: Ontology
- SpecIF:LifecycleStatus: SpecIF:LifecycleStatusReleased
- SpecIF:LocalTerm: Property (URI)
- SpecIF:LocalTermPlural: Properties (URI)
- SpecIF:isHeading: false
- SpecIF:Instantiation: user

## SpecIF:TermPropertyValue (SpecIF:TermResourceClass)
- SpecIF:Revision: 1.2
- dcterms:description: A term for SpecIF property values, often used in enumerated dataTypes.
- SpecIF:Domain: Ontology
- SpecIF:LifecycleStatus: SpecIF:LifecycleStatusReleased
- SpecIF:LocalTerm: Value
- SpecIF:LocalTermPlural: Values
- SpecIF:isHeading: false
- SpecIF:Instantiation: user

## IREB:Risk (SpecIF:TermResourceClass)
- dcterms:description: An event that threatens the success of an endeavor, e.g., of developing or operating a system. A risk is typically assessed in terms of its probability and potential damage.
- SpecIF:LocalTerm: Risk
- SpecIF:LifecycleStatus: SpecIF:LifecycleStatusReleased
- SpecIF:isHeading: false

## foaf:Person (SpecIF:TermResourceClass)
- dcterms:description: The Person class represents people. Something is a Person if it is a person. We don't nitpic about whether they're alive, dead, real, or imaginary. (source: FOAF)
- SpecIF:Domain: Requirement Engineering
- SpecIF:LifecycleStatus: SpecIF:LifecycleStatusEquivalent
- SpecIF:isHeading: false

## schema:Person (SpecIF:TermResourceClass)
- SpecIF:Revision: 1.2
- dcterms:description: A person (alive, dead, undead, or fictional).
- SpecIF:Domain: Requirement Engineering
- SpecIF:LifecycleStatus: SpecIF:LifecycleStatusReleased
- SpecIF:LocalTerm: Person
- SpecIF:LocalTermPlural: Persons
- SpecIF:isHeading: false
- SpecIF:Instantiation: user

## schema:Role (SpecIF:TermResourceClass)
- SpecIF:Revision: 1.2
- dcterms:description: Represents additional information about a relationship or property. For example a Role can be used to say that a 'member' role linking some SportsTeam to a player occurred during a particular time period. Or that a Person's 'actor' role in a Movie was for some particular characterName. Such properties can be attached to a Role entity, which is then associated with the main entities using ordinary properties like 'member' or 'actor'.
- SpecIF:Domain: Requirement Engineering
- SpecIF:LifecycleStatus: SpecIF:LifecycleStatusReleased
- SpecIF:LocalTerm: Role
- SpecIF:LocalTermPlural: Roles
- SpecIF:isHeading: false
- SpecIF:Instantiation: user

## schema:Organization (SpecIF:TermResourceClass)
- SpecIF:Revision: 1.2
- dcterms:description: An organization such as a school, NGO, corporation, club, etc.
- SpecIF:Domain: Requirement Engineering
- SpecIF:LifecycleStatus: SpecIF:LifecycleStatusReleased
- SpecIF:LocalTerm: Organisation
- SpecIF:LocalTermPlural: Organisationen
- SpecIF:isHeading: false
- SpecIF:Instantiation: user

## SpecIF:Hierarchy (SpecIF:TermResourceClass)
- dcterms:description: A root of a document structure with references to resources.
- SpecIF:LifecycleStatus: SpecIF:LifecycleStatusEquivalent
- SpecIF:isHeading: true

## SpecIF:Outline (SpecIF:TermResourceClass)
- SpecIF:Revision: 1.2
- dcterms:description: A root of a document structure with references to resources.
- SpecIF:Domain: Base, Requirement Engineering, Automotive Stakeholder Request Clarification Process, System Model Integration
- SpecIF:LifecycleStatus: SpecIF:LifecycleStatusReleased
- SpecIF:LocalTerm: Outline
- SpecIF:LocalTermPlural: Outlines
- SpecIF:isHeading: true
- SpecIF:Instantiation: user

## SpecIF:BillOfMaterials (SpecIF:TermResourceClass)
- SpecIF:Revision: 1.2
- dcterms:description: A bill of materials or product structure (sometimes bill of material, BOM or associated list) is a list of the raw materials, sub-assemblies, intermediate assemblies, sub-components, parts and the quantities of each needed to manufacture an end product. A BOM may be used for communication between manufacturing partners, or confined to a single manufacturing plant. (source: Wikipedia)
- SpecIF:Domain: System Model Integration
- SpecIF:LifecycleStatus: SpecIF:LifecycleStatusReleased
- SpecIF:isHeading: true
- SpecIF:Instantiation: user

## SpecIF:BusinessProcess (SpecIF:TermResourceClass)
- SpecIF:Revision: 1.2
- SpecIF:Domain: System Model Integration
- SpecIF:LifecycleStatus: SpecIF:LifecycleStatusEquivalent
- SpecIF:LocalTerm: Business Process
- SpecIF:isHeading: false
- SpecIF:Instantiation: auto

## SpecIF:BusinessProcesses (SpecIF:TermResourceClass)
- SpecIF:Revision: 1.2
- SpecIF:Domain: System Model Integration
- SpecIF:LifecycleStatus: SpecIF:LifecycleStatusReleased
- SpecIF:LocalTerm: Business Processes
- SpecIF:isHeading: false
- SpecIF:Instantiation: auto

## SpecIF:Glossary (SpecIF:TermResourceClass)
- SpecIF:Revision: 1.2
- SpecIF:Domain: Ontology
- SpecIF:LifecycleStatus: SpecIF:LifecycleStatusReleased
- SpecIF:LocalTerm: Model Elements (Glossary)
- SpecIF:isHeading: true
- SpecIF:Instantiation: user

## SpecIF:UnreferencedResources (SpecIF:TermResourceClass)
- SpecIF:Revision: 1.2
- SpecIF:Domain: Base
- SpecIF:LifecycleStatus: SpecIF:LifecycleStatusReleased
- SpecIF:LocalTerm: Unreferenced Resources (Recycle Bin)
- SpecIF:isHeading: true
- SpecIF:Instantiation: auto

## W3C:Vocabulary (SpecIF:TermResourceClass)
- SpecIF:Revision: 1.2
- SpecIF:LocalTerm: Vocabulary
- dcterms:description: A vocabulary according to the SpecIF class definitions for the domain 'Ontology'.

  There is no clear division between what is referred to as “vocabularies” and “ontologies”. The trend is to use the word “ontology” for more complex, and possibly quite formal collection of terms, whereas “vocabulary” is used when such strict formalism is not necessarily used or only in a very loose sense. Vocabularies are the basic building blocks for inference techniques on the Semantic Web.
- SpecIF:Domain: Ontology
- SpecIF:LifecycleStatus: SpecIF:LifecycleStatusEquivalent
- SpecIF:isHeading: true
- SpecIF:Instantiation: user

## W3C:Ontology (SpecIF:TermResourceClass)
- SpecIF:Revision: 1.2
- SpecIF:LocalTerm: Ontology
- dcterms:description: An ontology according to the SpecIF class definitions for the domain 'Ontology'.

  There is no clear division between what is referred to as “vocabularies” and “ontologies”. The trend is to use the word “ontology” for more complex, and possibly quite formal collection of terms, whereas “vocabulary” is used when such strict formalism is not necessarily used or only in a very loose sense. Vocabularies are the basic building blocks for inference techniques on the Semantic Web.
- SpecIF:Domain: Ontology
- SpecIF:LifecycleStatus: SpecIF:LifecycleStatusReleased
- SpecIF:isHeading: true
- SpecIF:Instantiation: user

## bpmn:Process (SpecIF:TermResourceClass)
- SpecIF:Revision: 1.2
- SpecIF:Domain: System Model Integration
- SpecIF:LifecycleStatus: SpecIF:LifecycleStatusReleased
- SpecIF:LocalTerm: Business Process
- SpecIF:LocalTermPlural: Business Processes
- SpecIF:isHeading: false
- SpecIF:Instantiation: auto

## bpmn:Participant (SpecIF:TermResourceClass)
- SpecIF:Revision: 1.2
- SpecIF:Domain: System Model Integration
- SpecIF:LifecycleStatus: SpecIF:LifecycleStatusReleased
- SpecIF:LocalTerm: Participant
- SpecIF:LocalTermPlural: Participants
- SpecIF:isHeading: false
- SpecIF:Instantiation: auto

## bpmn:Pool (SpecIF:TermResourceClass)
- SpecIF:Revision: 1.2
- SpecIF:Domain: System Model Integration
- SpecIF:LifecycleStatus: SpecIF:LifecycleStatusEquivalent
- SpecIF:LocalTerm: Pool
- SpecIF:LocalTermPlural: Pools
- SpecIF:isHeading: false
- SpecIF:Instantiation: auto

## bpmn:Lane (SpecIF:TermResourceClass)
- SpecIF:Revision: 1.2
- SpecIF:Domain: System Model Integration
- SpecIF:LifecycleStatus: SpecIF:LifecycleStatusEquivalent
- SpecIF:LocalTerm: Lane
- SpecIF:LocalTermPlural: Lanes
- SpecIF:isHeading: false
- SpecIF:Instantiation: auto

## UML:Actor (SpecIF:TermResourceClass)
- SpecIF:Revision: 1.2
- SpecIF:Domain: System Model Integration
- SpecIF:LifecycleStatus: SpecIF:LifecycleStatusReleased
- SpecIF:LocalTerm: Actor
- SpecIF:LocalTermPlural: Actors
- SpecIF:isHeading: false
- SpecIF:Instantiation: auto

## bpmn:processStep (SpecIF:TermResourceClass)
- dcterms:description: A defined value for the [[dcterms:type]] property of [[FMC:Actor]] when used to represent a process step.
- SpecIF:LifecycleStatus: SpecIF:LifecycleStatusExperimental
- SpecIF:LocalTerm: Process Step

## bpmn:startEvent (SpecIF:TermResourceClass)
- dcterms:description: A defined value for the [[dcterms:type]] property of [[FMC:Event]] when used to represent a general start event.
- SpecIF:LifecycleStatus: SpecIF:LifecycleStatusExperimental
- SpecIF:LocalTerm: Start Event

## bpmn:intermediateEvent (SpecIF:TermResourceClass)
- dcterms:description: A defined value for the [[dcterms:type]] property of [[FMC:Event]] when used to represent a general intermediate event.
- SpecIF:LifecycleStatus: SpecIF:LifecycleStatusExperimental
- SpecIF:LocalTerm: Intermediate Event

## bpmn:endEvent (SpecIF:TermResourceClass)
- dcterms:description: A defined value for the [[dcterms:type]] property of [[FMC:Event]] when used to represent a general end event.
- SpecIF:LifecycleStatus: SpecIF:LifecycleStatusExperimental
- SpecIF:LocalTerm: End Event

## bpmn:join (SpecIF:TermResourceClass)
- dcterms:description: A defined value for the [[dcterms:type]] property of [[FMC:Actor]] when used to represent a 'Join' element in models created with BPMN.
- SpecIF:LifecycleStatus: SpecIF:LifecycleStatusExperimental
- SpecIF:LocalTerm: Join

## bpmn:timer (SpecIF:TermResourceClass)
- dcterms:description: A defined value for the [[dcterms:type]] property of [[FMC:Actor]] when used to represent a 'Timer' element in models created with BPMN.
- SpecIF:LifecycleStatus: SpecIF:LifecycleStatusExperimental
- SpecIF:LocalTerm: Timer

## IREB:Stakeholder (SpecIF:TermResourceClass)
- dcterms:description: A person or organization that has a (direct or indirect) influence on a system’s requirements. Indirect influence also includes situations where a person or organization is impacted by the system.
  This is a subclass of [[FMC:Actor]], more precisely a value of it's property [[dcterms:type]].
- SpecIF:LifecycleStatus: SpecIF:LifecycleStatusReleased
- SpecIF:LocalTerm: Stakeholder

## ReqIF-WF.Customer (SpecIF:TermResourceClass)
- SpecIF:Revision: 1.2
- SpecIF:Domain: Automotive Stakeholder Request Clarification Process
- SpecIF:LifecycleStatus: SpecIF:LifecycleStatusReleased
- SpecIF:LocalTerm: Customer, Client, Purchaser

## ReqIF-WF.Supplier (SpecIF:TermResourceClass)
- SpecIF:Revision: 1.2
- SpecIF:Domain: Automotive Stakeholder Request Clarification Process
- SpecIF:LifecycleStatus: SpecIF:LifecycleStatusReleased
- SpecIF:LocalTerm: Supplier, Vendor, Service Provider, Contractor, Seller

## SpecIF:Reader (SpecIF:TermResourceClass)
- SpecIF:Revision: 1.2
- SpecIF:Domain: Requirement Engineering, Automotive Stakeholder Request Clarification Process, System Model Integration
- SpecIF:LifecycleStatus: SpecIF:LifecycleStatusReleased
- SpecIF:LocalTerm: Reader
- SpecIF:LocalTermPlural: Readers
- SpecIF:isHeading: false

## SpecIF:Editor (SpecIF:TermResourceClass)
- SpecIF:Revision: 1.2
- SpecIF:Domain: Requirement Engineering, Automotive Stakeholder Request Clarification Process, System Model Integration
- SpecIF:LifecycleStatus: SpecIF:LifecycleStatusReleased
- SpecIF:LocalTerm: Editor
- SpecIF:LocalTermPlural: Editors
- SpecIF:isHeading: false

## SpecIF:UserRole (SpecIF:TermResourceClass)
- dcterms:description: This is a subclass of [[FMC:Actor]]; more precisely a value of it's property [[dcterms:type]].
- SpecIF:LifecycleStatus: SpecIF:LifecycleStatusExperimental
- SpecIF:LocalTerm: User Role

## SpecIF:Feature (SpecIF:TermResourceClass)
- SpecIF:Revision: 1.2
- dcterms:description: A 'Feature' is an intentional distinguishing characteristic of a system, often a unique selling proposition.
- SpecIF:Domain: Requirement Engineering, Automotive Stakeholder Request Clarification Process, System Model Integration
- SpecIF:LifecycleStatus: SpecIF:LifecycleStatusReleased
- SpecIF:LocalTerm: Feature
- SpecIF:LocalTermPlural: Features
- SpecIF:Icon: ✶
- SpecIF:isHeading: false
- SpecIF:Instantiation: user

## SpecIF:UserStory (SpecIF:TermResourceClass)
- SpecIF:Revision: 1.2
- dcterms:description: A user story is an informal, general explanation of a software feature written from the perspective of the end user. Its purpose is to articulate how a software feature will provide value to the customer.
  This is a subclass of [[IREB:Requirement]], more precisely a value of it's property [[dcterms:type]].
- SpecIF:Domain: Requirement Engineering, Automotive Stakeholder Request Clarification Process, System Model Integration, Variant Management
- SpecIF:LifecycleStatus: SpecIF:LifecycleStatusReleased
- SpecIF:LocalTerm: User Story, User-Story
- SpecIF:LocalTermPlural: User Stories, User-Stories
- SpecIF:Icon: ☺

## SpecIF:PainPoint (SpecIF:TermResourceClass)
- SpecIF:Revision: 1.2
- dcterms:description: A problem, frustration, or troublesome issue, especially one experienced by consumers, customers, or employees: Getting stuck in a slow checkout line is a major pain point for grocery shoppers.
  This is a subclass of [[IREB:Requirement]], more precisely a value of it's property [[dcterms:type]].
- SpecIF:Domain: Requirement Engineering
- SpecIF:LifecycleStatus: SpecIF:LifecycleStatusReleased
- SpecIF:LocalTerm: Pain Point, Pain-Point
- SpecIF:Icon: ✂

## ArchiMate:DataObject (SpecIF:TermResourceClass)
- SpecIF:Revision: 1.2
- SpecIF:Domain: System Model Integration
- SpecIF:LifecycleStatus: SpecIF:LifecycleStatusReleased
- SpecIF:LocalTerm: Data Object
- SpecIF:LocalTermPlural: Data Objects

## DDP:Source (SpecIF:TermResourceClass)
- SpecIF:Revision: 1.2
- dcterms:description: A 'Source' is a file containing partial model information created by an authoring system.
- SpecIF:Domain: Requirement Engineering, Automotive Stakeholder Request Clarification Process, System Model Integration
- SpecIF:LifecycleStatus: SpecIF:LifecycleStatusSubmitted
- SpecIF:LocalTerm: Source File
- SpecIF:LocalTermPlural: Source Files
- SpecIF:Icon: 🗎
- SpecIF:isHeading: false
- SpecIF:Instantiation: auto, user

## Statement Class Terms (dcterms:title)
- dcterms:description: A statement represents a logic affinity or association between two resources, i.e. system specification artefacts. The terms listed in this chapter may be used as predicates to distinguish different classes (types) of statements. Each statement class may define an individual set of properties for carrying the information 'payload'.
  In SpecIF, a statement is first order predicate logic. For each predicate (statement class), a list of eligible resource classes may be defined for subjects and objects, respectively. For example, the predicate [[oslc_rm:satisfies]] is usually confined to [[FMC:Actor]] and [[FMC:State]] as subject and [[IREB:Requirement]] as object.
  A statement consisting of subject-predicate-object (where a resource may serve as subject or object) can be directly mapped to a ReqIF relation, a RDF triple in OSLC or 'linked data' in general.
  A statement class corresponds to a 'SPEC-RELATION-TYPE' and a statement is a 'SPEC-RELATION' in the Requirements Interchange Format (ReqIF). In ArchiMate® 3.0, a statement is a Relationship.

## SpecIF:relates (SpecIF:TermStatementClass)
- SpecIF:Revision: 1.2
- dcterms:description: Is a generalized type for model relations.
- SpecIF:Domain: Ontology
- SpecIF:LifecycleStatus: SpecIF:LifecycleStatusSubmitted
- SpecIF:LocalTerm: Model Relation
- SpecIF:isUndirected: false
- SpecIF:Instantiation: auto

## SpecIF:shows (SpecIF:TermStatementClass)
- dcterms:identifier: SC-shows
- SpecIF:Revision: 1.1
- dcterms:description: A [[SpecIF:Diagram]] 'shows' a model element, e.g, a [[FMC:Actor]], [[FMC:State]], [[FMC:Event]] or [[SpecIF:Collection]].
- SpecIF:LocalTerm: shows
- SpecIF:Domain: System Model Integration
- SpecIF:LifecycleStatus: SpecIF:LifecycleStatusReleased
- SpecIF:isUndirected: false
- SpecIF:Instantiation: auto

## SpecIF:contains (SpecIF:TermStatementClass)
- SpecIF:Revision: 1.2
- dcterms:description: General containment, such as:
  - Component-A contains Component-B
  - DataObject-1 contains Attribute-1.1
- SpecIF:Domain: System Model Integration
- SpecIF:LifecycleStatus: SpecIF:LifecycleStatusReleased
- SpecIF:LocalTerm: contains
- SpecIF:isUndirected: false
- SpecIF:Instantiation: auto

## ArchiMate:unites (SpecIF:TermStatementClass)
- SpecIF:Revision: 1.2
- dcterms:description: General containment. In ArchiMate, the uniting concept includes:
  - The *composition* relationship represents that an element consists of one or more other concepts.
  - The *aggregation* relationship represents that an element combines one or more other concepts.
  - The *assignment* relationship represents the allocation of responsibility, performance of behavior, storage, or execution.
  - The *realization* relationship represents that an entity plays a critical role in the creation, achievement, sustenance, or operation of a more abstract entity.

  The kind of uniting is specified in a property with title [[dcterms:type]].
- SpecIF:Domain: System Model Integration
- SpecIF:LifecycleStatus: SpecIF:LifecycleStatusEquivalent
- SpecIF:LocalTerm: unites
- SpecIF:isUndirected: false
- SpecIF:Instantiation: auto

## FMC:contains (SpecIF:TermStatementClass)
- SpecIF:Revision: 1.2
- dcterms:description: A [[FMC:Actor]] or [[FMC:State]] 'contains' a [[FMC:Actor]], [[FMC:State]] or [[FMC:Event]]. More concretely, Component-A contains Component-B.
- SpecIF:Domain: System Model Integration
- SpecIF:LifecycleStatus: SpecIF:LifecycleStatusReleased
- SpecIF:LocalTerm: contains
- SpecIF:isUndirected: false
- SpecIF:Instantiation: auto

## SpecIF:satisfies (SpecIF:TermStatementClass)
- dcterms:description: A [[FMC:Actor]] or [[FMC:State]] 'satisfies' a [[IREB:Requirement]].
- SpecIF:LocalTerm: satisfies
- SpecIF:LifecycleStatus: SpecIF:LifecycleStatusEquivalent

## SpecIF:implements (SpecIF:TermStatementClass)
- dcterms:description: A [[FMC:Actor]] or [[FMC:State]] 'implements' a [[SpecIF:Feature]].
- SpecIF:LifecycleStatus: SpecIF:LifecycleStatusEquivalent
- SpecIF:LocalTerm: implements
- SpecIF:isUndirected: false

## SpecIF:influences (SpecIF:TermStatementClass)
- dcterms:description: The influence relationship represents that an element affects the implementation or achievement of some motivation element.
- SpecIF:LocalTerm: influences
- SpecIF:Domain: System Model Integration
- SpecIF:LifecycleStatus: SpecIF:LifecycleStatusExperimental

## rdf:type (SpecIF:TermStatementClass)
- dcterms:description: A triple of the form: R rdf:type C states that C is an instance of rdfs:Class and R is an instance of C.
  The rdfs:domain of rdf:type is rdfs:Resource. The rdfs:range of rdf:type is rdfs:Class.
- SpecIF:LocalTerm: Type
- SpecIF:Domain: System Model Integration
- SpecIF:LifecycleStatus: SpecIF:LifecycleStatusReleased
- SpecIF:isUndirected: false

## oslc_rm:satisfies (SpecIF:TermStatementClass)
- dcterms:description: The object is satisfied by the subject. (source: OSLC)
  SpecIF suggests that the subject is confined to a model element, e.g, a [[FMC:Actor]] or [[FMC:State]], and the object is confined to a [[IREB:Requirement]]. More concretely, an example for this type of statement is 'Component-X satisfies 'Requirement-4711'.
- SpecIF:LocalTerm: satisfies
- SpecIF:LifecycleStatus: SpecIF:LifecycleStatusReleased
- SpecIF:isUndirected: false
- SpecIF:Instantiation: user

## oslc_rm:satisfiedBy (SpecIF:TermStatementClass)
- SpecIF:Revision: 1.2
- dcterms:description: The subject is satisfied by the object. For example, a user requirement is satisfied by a system requirement. (source: OSLC)
- SpecIF:LocalTerm: satisfied by
- SpecIF:Domain: Requirement Engineering, Automotive Stakeholder Request Clarification Process
- SpecIF:LifecycleStatus: SpecIF:LifecycleStatusReleased
- SpecIF:isUndirected: false
- SpecIF:Instantiation: user

## oslc_rm:elaborates (SpecIF:TermStatementClass)
- dcterms:description: The object is elaborated by the subject. For example, a use case elaborates a requirement.
- SpecIF:LifecycleStatus: SpecIF:LifecycleStatusEquivalent
- SpecIF:isUndirected: false

## oslc_rm:elaboratedBy (SpecIF:TermStatementClass)
- dcterms:description: The subject is elaborated by the object.

## oslc_rm:specifies (SpecIF:TermStatementClass)
- dcterms:description: The object is specified by the subject. For example, a requirement specifies a model element.

## oslc_rm:specifiedBy (SpecIF:TermStatementClass)
- dcterms:description: The subject is specified by the object.

## oslc_rm:affectedBy (SpecIF:TermStatementClass)
- dcterms:description: Requirement is affected by a resource, such as a defect or issue.

## oslc_rm:trackedBy (SpecIF:TermStatementClass)
- dcterms:description: Resource, such as a change request, which tracks this requirement.

## oslc_rm:implementedBy (SpecIF:TermStatementClass)
- dcterms:description: Resource, such as a change request, which implements this requirement.
- SpecIF:Domain: System Model Integration
- SpecIF:LifecycleStatus: SpecIF:LifecycleStatusReleased
- SpecIF:LocalTerm: implemented by
- SpecIF:isUndirected: false

## oslc_rm:implements (SpecIF:TermStatementClass)
- dcterms:description: Resource, such as a change request, which implements this requirement.
- SpecIF:Domain: System Model Integration
- SpecIF:LifecycleStatus: SpecIF:LifecycleStatusReleased
- SpecIF:LocalTerm: implements
- SpecIF:isUndirected: false

## oslc_rm:validatedBy (SpecIF:TermStatementClass)
- dcterms:description: Resource, such as a test case, which validates this requirement.
- SpecIF:Domain: System Testing
- SpecIF:LifecycleStatus: SpecIF:LifecycleStatusSubmitted
- SpecIF:LocalTerm: validated by
- SpecIF:isUndirected: false

## oslc_rm:validates (SpecIF:TermStatementClass)
- dcterms:description: Resource, such as a test case, which validates this requirement.
- SpecIF:Domain: System Testing
- SpecIF:LocalTerm: validates
- SpecIF:isUndirected: false

## oslc_rm:decomposes (SpecIF:TermStatementClass)
- dcterms:description: The object is decomposed by the subject. For example, a collection of subsystems decomposes a system.
- SpecIF:Domain: System Model Integration
- SpecIF:LifecycleStatus: SpecIF:LifecycleStatusSubmitted
- SpecIF:LocalTerm: decomposes
- SpecIF:isUndirected: false

## oslc_rm:decomposedBy (SpecIF:TermStatementClass)
- dcterms:description: The subject is decomposed by the object.
- SpecIF:Domain: System Model Integration
- SpecIF:LocalTerm: decomposed by
- SpecIF:isUndirected: false

## oslc_rm:constrains (SpecIF:TermStatementClass)
- dcterms:description: The object is constrained by the subject. For example, a safety requirement constrains a functional requirement.
- SpecIF:Domain: System Model Integration
- SpecIF:LocalTerm: constrains

## oslc_rm:constrainedBy (SpecIF:TermStatementClass)
- dcterms:description: The subject is constrained by the object.
- SpecIF:LocalTerm: constrained by

## SpecIF:serves (SpecIF:TermStatementClass)
- SpecIF:Revision: 1.2
- dcterms:description: A [[FMC:Actor]] 'serves' a FMC:Actor.
- SpecIF:Domain: System Model Integration
- SpecIF:LifecycleStatus: SpecIF:LifecycleStatusEquivalent
- SpecIF:LocalTerm: serves
- SpecIF:isUndirected: false
- SpecIF:Instantiation: auto

## ArchiMate:serves (SpecIF:TermStatementClass)
- SpecIF:Revision: 1.2
- dcterms:description: The serving relationship represents that an element provides its functionality to another element. (Quelle: ArchiMate 3.1. Relationships)
- SpecIF:Domain: System Model Integration
- SpecIF:LifecycleStatus: SpecIF:LifecycleStatusReleased
- SpecIF:LocalTerm: serves
- SpecIF:isUndirected: false
- SpecIF:Instantiation: auto

## SpecIF:reads (SpecIF:TermStatementClass)
- SpecIF:Revision: 1.2
- dcterms:description: A [[FMC:Actor]] 'reads' a [[FMC:State]].
- SpecIF:LocalTerm: reads
- SpecIF:Domain: System Model Integration
- SpecIF:LifecycleStatus: SpecIF:LifecycleStatusReleased
- SpecIF:isUndirected: false
- SpecIF:Instantiation: auto

## SpecIF:writes (SpecIF:TermStatementClass)
- SpecIF:Revision: 1.2
- dcterms:description: A [[FMC:Actor]] 'writes' (changes) a [[FMC:State]].
- SpecIF:LocalTerm: writes
- SpecIF:Domain: System Model Integration
- SpecIF:LifecycleStatus: SpecIF:LifecycleStatusReleased
- SpecIF:isUndirected: false
- SpecIF:Instantiation: auto

## SpecIF:stores (SpecIF:TermStatementClass)
- SpecIF:Revision: 1.2
- dcterms:description: A [[FMC:Actor]] 'stores' (writes and reads) a [[FMC:State]].
- SpecIF:Domain: System Model Integration
- SpecIF:LifecycleStatus: SpecIF:LifecycleStatusEquivalent
- SpecIF:LocalTerm: stores
- SpecIF:isUndirected: false
- SpecIF:Instantiation: auto

## SpecIF:accesses (SpecIF:TermStatementClass)
- SpecIF:Revision: 1.2
- dcterms:description: A [[FMC:Actor]] 'accesses' (writes and reads) a [[FMC:State]].
- SpecIF:Domain: System Model Integration
- SpecIF:LifecycleStatus: SpecIF:LifecycleStatusEquivalent
- SpecIF:LocalTerm: accesses, stores
- SpecIF:isUndirected: false
- SpecIF:Instantiation: auto

## ArchiMate:accesses (SpecIF:TermStatementClass)
- dcterms:description: A [[FMC:Actor]] 'accesses' (writes and reads) a [[FMC:State]].
- SpecIF:Domain: System Model Integration
- SpecIF:LifecycleStatus: SpecIF:LifecycleStatusReleased
- SpecIF:LocalTerm: accesses, stores
- SpecIF:isUndirected: false
- SpecIF:Instantiation: auto

## ArchiMate:realizes (SpecIF:TermStatementClass)
- dcterms:description: A business function realizes a business capability or an application component realizes a business function.
- SpecIF:Domain: System Model Integration
- SpecIF:LifecycleStatus: SpecIF:LifecycleStatusReleased
- SpecIF:LocalTerm: realizes
- SpecIF:isUndirected: false
- SpecIF:Instantiation: auto

## SpecIF:realizes (SpecIF:TermStatementClass)
- dcterms:description: A business function realizes a business capability or an application component realizes a business function.
- SpecIF:Domain: System Model Integration
- SpecIF:LifecycleStatus: SpecIF:LifecycleStatusEquivalent
- SpecIF:LocalTerm: realizes
- SpecIF:isUndirected: false
- SpecIF:Instantiation: auto

## ArchiMate:isAssignedTo (SpecIF:TermStatementClass)
- dcterms:description: The assignment relationship represents the allocation of responsibility, performance of behavior, storage, or execution.
- SpecIF:Domain: System Model Integration
- SpecIF:LifecycleStatus: SpecIF:LifecycleStatusReleased
- SpecIF:LocalTerm: assigned to
- SpecIF:isUndirected: false
- SpecIF:Instantiation: auto

## ArchiMate:isRealizedBy (SpecIF:TermStatementClass)
- dcterms:description: A business capability is realized by a business function or a business function is realized by an application component.
- SpecIF:Domain: System Model Integration
- SpecIF:LifecycleStatus: SpecIF:LifecycleStatusReleased
- SpecIF:LocalTerm: wird realisiert von
- SpecIF:isUndirected: false
- SpecIF:Instantiation: auto

## FMC:modifies (SpecIF:TermStatementClass)
- dcterms:description: A [[FMC:Actor]] writes *and* reads a [[FMC:State]].
- SpecIF:LocalTerm: modifies
- SpecIF:Domain: System Model Integration
- SpecIF:LifecycleStatus: SpecIF:LifecycleStatusEquivalent

## FMC:communicatesWith (SpecIF:TermStatementClass)
- SpecIF:Revision: 1.2
- dcterms:description: A [[FMC:Actor]] 'communicates' with a [[FMC:Actor]].
- SpecIF:LocalTerm: communicates with
- SpecIF:Domain: System Model Integration
- SpecIF:LifecycleStatus: SpecIF:LifecycleStatusReleased
- SpecIF:isUndirected: false
- SpecIF:Instantiation: auto

## FMC:sendsTo (SpecIF:TermStatementClass)
- SpecIF:Revision: 1.2
- dcterms:description: A [[FMC:Actor]] 'sends' a message to a [[FMC:Actor]].
- SpecIF:LocalTerm: sends to
- SpecIF:Domain: System Model Integration
- SpecIF:LifecycleStatus: SpecIF:LifecycleStatusReleased
- SpecIF:isUndirected: false
- SpecIF:Instantiation: auto

## FMC:receivesFrom (SpecIF:TermStatementClass)
- SpecIF:Revision: 1.2
- dcterms:description: A [[FMC:Actor]] 'receives' a message from a [[FMC:Actor]].
- SpecIF:LocalTerm: receives from
- SpecIF:Domain: System Model Integration
- SpecIF:LifecycleStatus: SpecIF:LifecycleStatusReleased
- SpecIF:isUndirected: false
- SpecIF:Instantiation: auto

## SpecIF:follows (SpecIF:TermStatementClass)
- SpecIF:Revision: 1.2
- dcterms:description: A [[FMC:Actor]] 'follows' a [[FMC:Actor]]; e.g. in a business process or activity flow.
- SpecIF:Domain: System Model Integration
- SpecIF:LifecycleStatus: SpecIF:LifecycleStatusReleased
- SpecIF:LocalTerm: follows
- SpecIF:isUndirected: false
- SpecIF:Instantiation: auto

## SpecIF:precedes (SpecIF:TermStatementClass)
- SpecIF:Revision: 1.2
- dcterms:description: A [[FMC:Actor]] 'precedes' a [[FMC:Actor]]; e.g. in a business process or activity flow.
- SpecIF:Domain: System Model Integration
- SpecIF:LifecycleStatus: SpecIF:LifecycleStatusReleased
- SpecIF:LocalTerm: precedes
- SpecIF:isUndirected: false
- SpecIF:Instantiation: auto

## SpecIF:signals (SpecIF:TermStatementClass)
- dcterms:description: A [[FMC:Actor]] 'signals' a [[FMC:Event]].
- SpecIF:Domain: System Model Integration
- SpecIF:LifecycleStatus: SpecIF:LifecycleStatusDeprecated
- SpecIF:LocalTerm: signals
- SpecIF:isUndirected: false

## SpecIF:triggers (SpecIF:TermStatementClass)
- dcterms:description: A [[FMC:Event]] 'triggers' a [[FMC:Actor]].
- SpecIF:Domain: System Model Integration
- SpecIF:LifecycleStatus: SpecIF:LifecycleStatusDeprecated
- SpecIF:LocalTerm: triggers
- SpecIF:isUndirected: false

## SpecIF:dependsOn (SpecIF:TermStatementClass)
- SpecIF:Revision: 1.2
- dcterms:description: A [[IREB:Requirement]] 'depends on' another [[IREB:Requirement]].
- SpecIF:Domain: Requirement Engineering, Automotive Stakeholder Request Clarification Process, System Model Integration
- SpecIF:LifecycleStatus: SpecIF:LifecycleStatusReleased
- SpecIF:LocalTerm: depends on
- SpecIF:isUndirected: false
- SpecIF:Instantiation: user

## SysML:traces (SpecIF:TermStatementClass)
- SpecIF:Revision: 1.2
- dcterms:description: A [[IREB:Requirement]] traces another [[IREB:Requirement]]. This is the most general (yet unspecified) relation between resources.
- SpecIF:Domain: Requirement Engineering, Automotive Stakeholder Request Clarification Process, System Model Integration
- SpecIF:LifecycleStatus: SpecIF:LifecycleStatusSubmitted
- SpecIF:isUndirected: false
- SpecIF:Instantiation: user

## SysML:isDerivedFrom (SpecIF:TermStatementClass)
- SpecIF:Revision: 1.2
- dcterms:description: A [[IREB:Requirement]] 'is derived from' another [[IREB:Requirement]].
- SpecIF:Domain: Requirement Engineering, Automotive Stakeholder Request Clarification Process, System Model Integration
- SpecIF:LifecycleStatus: SpecIF:LifecycleStatusReleased
- SpecIF:LocalTerm: derived from
- SpecIF:isUndirected: false
- SpecIF:Instantiation: user

## IREB:refines (SpecIF:TermStatementClass)
- SpecIF:Revision: 1.2
- dcterms:description: A [[IREB:Requirement]] 'refines' another [[IREB:Requirement]].
- SpecIF:Domain: Requirement Engineering
- SpecIF:LifecycleStatus: SpecIF:LifecycleStatusReleased
- SpecIF:LocalTerm: refines
- SpecIF:isUndirected: false
- SpecIF:Instantiation: user

## IREB:refinedBy (SpecIF:TermStatementClass)
- SpecIF:Revision: 1.2
- dcterms:description: A [[IREB:Requirement]] 'is refined by' another [[IREB:Requirement]].
- SpecIF:Domain: Requirement Engineering
- SpecIF:LifecycleStatus: SpecIF:LifecycleStatusReleased
- SpecIF:LocalTerm: refined by
- SpecIF:isUndirected: false
- SpecIF:Instantiation: user

## SpecIF:duplicates (SpecIF:TermStatementClass)
- SpecIF:Revision: 1.2
- dcterms:description: A [[IREB:Requirement]] 'duplicates' another [[IREB:Requirement]].
- SpecIF:Domain: Requirement Engineering
- SpecIF:LifecycleStatus: SpecIF:LifecycleStatusReleased
- SpecIF:LocalTerm: duplicates
- SpecIF:isUndirected: true
- SpecIF:Instantiation: user

## SpecIF:contradicts (SpecIF:TermStatementClass)
- SpecIF:Revision: 1.2
- dcterms:description: A [[IREB:Requirement]] 'contradicts' another [[IREB:Requirement]].
- SpecIF:Domain: Requirement Engineering
- SpecIF:LifecycleStatus: SpecIF:LifecycleStatusReleased
- SpecIF:LocalTerm: contradicts
- SpecIF:isUndirected: true
- SpecIF:Instantiation: user

## SysML:isAllocatedTo (SpecIF:TermStatementClass)
- SpecIF:Revision: 1.2
- dcterms:description: An [[FMC:Actor]] is allocated to another [[FMC:Actor]] (e.g. a logical function is allocated to a physical component.
- SpecIF:Domain: System Model Integration
- SpecIF:LifecycleStatus: SpecIF:LifecycleStatusReleased
- SpecIF:LocalTerm: allocated to
- SpecIF:isUndirected: false
- SpecIF:Instantiation: auto

## UML:isAssociatedWith (SpecIF:TermStatementClass)
- SpecIF:Revision: 1.2
- dcterms:description: A [[FMC:State]] is associated with another [[FMC:State]] (e.g. a class is associated with another class, as shown in a UML Class Diagram).
- SpecIF:Domain: System Model Integration
- SpecIF:LifecycleStatus: SpecIF:LifecycleStatusReleased
- SpecIF:LocalTerm: associated with
- SpecIF:isUndirected: false
- SpecIF:Instantiation: auto

## SpecIF:isAssociatedWith (SpecIF:TermStatementClass)
- dcterms:description: A [[FMC:State]] is associated with another [[FMC:State]] (e.g. a class is associated with another class, as shown in a UML Class Diagram).
- SpecIF:LifecycleStatus: SpecIF:LifecycleStatusEquivalent
- SpecIF:LocalTerm: associated with
- SpecIF:isUndirected: false
- SpecIF:Instantiation: auto

## SysML:isAssociatedWith (SpecIF:TermStatementClass)
- dcterms:description: A [[FMC:State]] is associated with another [[FMC:State]] (e.g. a class is associated with another class, as shown in a UML Class Diagram).
- SpecIF:Domain: System Model Integration
- SpecIF:LifecycleStatus: SpecIF:LifecycleStatusEquivalent
- SpecIF:isUndirected: false
- SpecIF:Instantiation: auto

## UML:isComposedOf (SpecIF:TermStatementClass)
- SpecIF:Revision: 1.2
- dcterms:description: An [[FMC:Actor]] is composed of another [[FMC:Actor]].
- SpecIF:Domain: System Model Integration
- SpecIF:LifecycleStatus: SpecIF:LifecycleStatusReleased
- SpecIF:LocalTerm: composed of
- SpecIF:isUndirected: false
- SpecIF:Instantiation: auto

## SysML:isComposedOf (SpecIF:TermStatementClass)
- dcterms:description: An [[FMC:Actor]] is composed of another [[FMC:Actor]].
- SpecIF:Domain: System Model Integration
- SpecIF:LifecycleStatus: SpecIF:LifecycleStatusExperimental
- SpecIF:LocalTerm: composed of
- SpecIF:isUndirected: false
- SpecIF:Instantiation: auto

## ArchiMate:isComposedOf (SpecIF:TermStatementClass)
- SpecIF:Revision: 1.2
- dcterms:description: An [[FMC:Actor]] is composed of another [[FMC:Actor]].
- SpecIF:Domain: System Model Integration
- SpecIF:LifecycleStatus: SpecIF:LifecycleStatusExperimental
- SpecIF:LocalTerm: composes
- SpecIF:isUndirected: false
- SpecIF:Instantiation: auto

## ArchiMate:composes (SpecIF:TermStatementClass)
- SpecIF:Revision: 1.2
- dcterms:description: An [[FMC:Actor]] composes another [[FMC:Actor]].
  The things that something is composed of are its parts or members. The separate things that compose something are the parts or members that form it. Source: Collins Dictionary
- SpecIF:Domain: System Model Integration
- SpecIF:LifecycleStatus: SpecIF:LifecycleStatusExperimental
- SpecIF:LocalTerm: composes
- SpecIF:isUndirected: false
- SpecIF:Instantiation: auto

## UML:composes (SpecIF:TermStatementClass)
- SpecIF:Revision: 1.2
- dcterms:description: An [[FMC:Actor]] is composed of another [[FMC:Actor]].
  The things that something is composed of are its parts or members. The separate things that compose something are the parts or members that form it. Source: Collins Dictionary
- SpecIF:Domain: System Model Integration
- SpecIF:LifecycleStatus: SpecIF:LifecycleStatusReleased
- SpecIF:LocalTerm: composes
- SpecIF:isUndirected: false
- SpecIF:Instantiation: auto

## UML:isAggregatedBy (SpecIF:TermStatementClass)
- SpecIF:Revision: 1.2
- dcterms:description: An [[FMC:Actor]] is aggregated by another [[FMC:Actor]].
- SpecIF:Domain: System Model Integration
- SpecIF:LifecycleStatus: SpecIF:LifecycleStatusReleased
- SpecIF:LocalTerm: aggregated by
- SpecIF:isUndirected: false
- SpecIF:Instantiation: auto

## SysML:isAggregatedBy (SpecIF:TermStatementClass)
- SpecIF:Revision: 1.2
- dcterms:description: An [[FMC:Actor]] is aggregated by another [[FMC:Actor]].
- SpecIF:Domain: System Model Integration
- SpecIF:LifecycleStatus: SpecIF:LifecycleStatusEquivalent
- SpecIF:LocalTerm: aggregated by
- SpecIF:isUndirected: false
- SpecIF:Instantiation: auto

## UML:aggregates (SpecIF:TermStatementClass)
- SpecIF:Revision: 1.2
- dcterms:description: An [[FMC:Actor]] aggregates another [[FMC:Actor]].
  If amounts or things are aggregated, they are added together and considered as a single amount or thing.Source: Collins Dictionary
- SpecIF:Domain: System Model Integration
- SpecIF:LifecycleStatus: SpecIF:LifecycleStatusReleased
- SpecIF:LocalTerm: aggregates
- SpecIF:isUndirected: false
- SpecIF:Instantiation: auto

## SysML:aggregates (SpecIF:TermStatementClass)
- dcterms:description: An [[FMC:Actor]] aggregates another [[FMC:Actor]].
  If amounts or things are aggregated, they are added together and considered as a single amount or thing.Source: Collins Dictionary
- SpecIF:Domain: System Model Integration
- SpecIF:LifecycleStatus: SpecIF:LifecycleStatusEquivalent
- SpecIF:LocalTerm: aggregates
- SpecIF:isUndirected: false
- SpecIF:Instantiation: auto

## ArchiMate:aggregates (SpecIF:TermStatementClass)
- SpecIF:Revision: 1.2
- dcterms:description: An [[FMC:Actor]] aggregates another [[FMC:Actor]].
  If amounts or things are aggregated, they are added together and considered as a single amount or thing.Source: Collins Dictionary
- SpecIF:Domain: System Model Integration
- SpecIF:LifecycleStatus: SpecIF:LifecycleStatusEquivalent
- SpecIF:LocalTerm: aggregates
- SpecIF:isUndirected: false
- SpecIF:Instantiation: auto

## SysML:uses (SpecIF:TermStatementClass)
- SpecIF:Revision: 1.2
- SpecIF:Domain: System Model Integration
- SpecIF:LifecycleStatus: SpecIF:LifecycleStatusReleased
- SpecIF:LocalTerm: uses
- SpecIF:isUndirected: false
- SpecIF:Instantiation: auto

## SysML:isUsedBy (SpecIF:TermStatementClass)
- SpecIF:Revision: 1.2
- SpecIF:Domain: System Model Integration
- SpecIF:LifecycleStatus: SpecIF:LifecycleStatusReleased
- SpecIF:LocalTerm: used by
- SpecIF:isUndirected: false
- SpecIF:Instantiation: auto

## UML:extends (SpecIF:TermStatementClass)
- SpecIF:Revision: 1.2
- dcterms:description: An [[FMC:Actor]] «UseCase» extends another [[FMC:Actor]] «UseCase».
- SpecIF:Domain: System Model Integration
- SpecIF:LifecycleStatus: SpecIF:LifecycleStatusReleased
- SpecIF:LocalTerm: extends
- SpecIF:isUndirected: false
- SpecIF:Instantiation: auto

## SysML:extends (SpecIF:TermStatementClass)
- SpecIF:Revision: 1.2
- dcterms:description: An [[FMC:Actor]] «UseCase» extends another [[FMC:Actor]] «UseCase».
- SpecIF:Domain: System Model Integration
- SpecIF:LifecycleStatus: SpecIF:LifecycleStatusEquivalent
- SpecIF:LocalTerm: extends
- SpecIF:isUndirected: false
- SpecIF:Instantiation: auto

## SysML:includes (SpecIF:TermStatementClass)
- SpecIF:Revision: 1.2
- dcterms:description: An [[FMC:Actor]] «UseCase» includes another [[FMC:Actor]] «UseCase».
- SpecIF:Domain: System Model Integration
- SpecIF:LifecycleStatus: SpecIF:LifecycleStatusReleased
- SpecIF:LocalTerm: includes
- SpecIF:isUndirected: false
- SpecIF:Instantiation: auto

## UML:isSpecializationOf (SpecIF:TermStatementClass)
- SpecIF:Revision: 1.2
- dcterms:description: A [[FMC:Actor]] is a specialization of another [[FMC:Actor]]; similarly for [[FMC:State]] and [[FMC:Event]].
- SpecIF:Domain: System Model Integration
- SpecIF:LifecycleStatus: SpecIF:LifecycleStatusReleased
- SpecIF:LocalTerm: specializes
- SpecIF:isUndirected: false
- SpecIF:Instantiation: auto

## UML:isSpecialisationOf (SpecIF:TermStatementClass)
- SpecIF:Domain: System Model Integration
- SpecIF:LifecycleStatus: SpecIF:LifecycleStatusDeprecated
- SpecIF:LocalTerm: specializes
- SpecIF:isUndirected: false

## UML:isGeneralizationOf (SpecIF:TermStatementClass)
- SpecIF:Revision: 1.2
- dcterms:description: A [[FMC:Actor]] is a generalization of another [[FMC:Actor]]; similarly for [[FMC:State]] and [[FMC:Event]].
- SpecIF:Domain: System Model Integration
- SpecIF:LifecycleStatus: SpecIF:LifecycleStatusReleased
- SpecIF:LocalTerm: generalizes
- SpecIF:isUndirected: false
- SpecIF:Instantiation: auto

## UML:isGeneralisationOf (SpecIF:TermStatementClass)
- SpecIF:Domain: System Model Integration
- SpecIF:LifecycleStatus: SpecIF:LifecycleStatusDeprecated

## SpecIF:isSpecializationOf (SpecIF:TermStatementClass)
- dcterms:description: A FMC:Actor is a specialization of another FMC:Actor; similarly for FMC:State and FMC:Event.
- SpecIF:Domain: System Model Integration
- SpecIF:LifecycleStatus: SpecIF:LifecycleStatusEquivalent
- SpecIF:Instantiation: auto

## SysML:isSpecializationOf (SpecIF:TermStatementClass)
- dcterms:description: A FMC:Actor is a specialization of another FMC:Actor; similarly for FMC:State and FMC:Event.
- SpecIF:Domain: System Model Integration
- SpecIF:LifecycleStatus: SpecIF:LifecycleStatusEquivalent
- SpecIF:isUndirected: false

## SpecIF:isGeneralizationOf (SpecIF:TermStatementClass)
- dcterms:description: A FMC:Actor is a generalization of another FMC:Actor; similarly for FMC:State and FMC:Event.
- SpecIF:Domain: System Model Integration
- SpecIF:LifecycleStatus: SpecIF:LifecycleStatusEquivalent
- SpecIF:Instantiation: auto

## SysML:isGeneralizationOf (SpecIF:TermStatementClass)
- dcterms:description: A FMC:Actor is a generalization of another FMC:Actor; similarly for FMC:State and FMC:Event.
- SpecIF:Domain: System Model Integration
- SpecIF:LifecycleStatus: SpecIF:LifecycleStatusEquivalent
- SpecIF:isUndirected: false

## SpecIF:inheritsFrom (SpecIF:TermStatementClass)
- dcterms:description: A model-element class inherits from another. For example a data-object of class [[FMC:State]] inherits from another data-object, as shown in a UML Class Diagram).
- SpecIF:LifecycleStatus: SpecIF:LifecycleStatusReleased
- SpecIF:LocalTerm: inherits from
- SpecIF:isUndirected: false

## IR:inheritsFrom (SpecIF:TermStatementClass)
- dcterms:description: A model-element class inherits from another.
- SpecIF:LifecycleStatus: SpecIF:LifecycleStatusEquivalent
- SpecIF:LocalTerm: inherits from
- SpecIF:isUndirected: false

## SpecIF:refersTo (SpecIF:TermStatementClass)
- dcterms:identifier: SC-refersTo
- SpecIF:Revision: 1.2
- dcterms:description: A resource 'refers to' any other resource.
- SpecIF:Domain: Base
- SpecIF:LifecycleStatus: SpecIF:LifecycleStatusReleased
- SpecIF:LocalTerm: refers to
- SpecIF:isUndirected: false

## IR:refersTo (SpecIF:TermStatementClass)
- dcterms:description: An Interaction-Room annotation 'refers to' any other model element.
- SpecIF:Domain: System Model Integration
- SpecIF:LifecycleStatus: SpecIF:LifecycleStatusEquivalent
- SpecIF:LocalTerm: refers to
- SpecIF:isUndirected: false
- SpecIF:Instantiation: user

## IR:approves (SpecIF:TermStatementClass)
- SpecIF:Revision: 1.2
- SpecIF:Domain: System Model Integration
- SpecIF:LifecycleStatus: SpecIF:LifecycleStatusReleased
- SpecIF:LocalTerm: supports
- SpecIF:isUndirected: false
- SpecIF:Instantiation: user

## IR:opposes (SpecIF:TermStatementClass)
- SpecIF:Revision: 1.2
- SpecIF:Domain: System Model Integration
- SpecIF:LifecycleStatus: SpecIF:LifecycleStatusReleased
- SpecIF:LocalTerm: opposes
- SpecIF:isUndirected: false
- SpecIF:Instantiation: user

## SpecIF:commentRefersTo (SpecIF:TermStatementClass)
- SpecIF:Revision: 1.2
- dcterms:description: A [[SpecIF:Comment]] 'refers to' any other resource.
- SpecIF:Domain: Base
- SpecIF:LifecycleStatus: SpecIF:LifecycleStatusReleased
- SpecIF:LocalTerm: refers to
- SpecIF:isUndirected: false
- SpecIF:Instantiation: auto

## SpecIF:issueRefersTo (SpecIF:TermStatementClass)
- SpecIF:Revision: 1.2
- dcterms:description: A [[SpecIF:Issue]] 'refers to' any other resource.
- SpecIF:Domain: Base
- SpecIF:LifecycleStatus: SpecIF:LifecycleStatusReleased
- SpecIF:LocalTerm: refers to
- SpecIF:isUndirected: false
- SpecIF:Instantiation: auto

## SpecIF:mentions (SpecIF:TermStatementClass)
- dcterms:description: A resource's text refers to another resource (e.g. by hyperlink).
- SpecIF:Domain: Base
- SpecIF:LifecycleStatus: SpecIF:LifecycleStatusReleased
- SpecIF:LocalTerm: mentions
- SpecIF:isUndirected: false

## SpecIF:isSynonymOf (SpecIF:TermStatementClass)
- SpecIF:Revision: 1.2
- dcterms:description: A term is synonymous with another term, if both represent the same concept.
  According to Wikipedia, a synonym is a word or phrase that means exactly or nearly the same as another word or phrase in the same language. Words that are synonyms are said to be synonymous.
- SpecIF:Domain: Ontology
- SpecIF:LifecycleStatus: SpecIF:LifecycleStatusReleased
- SpecIF:LocalTerm: Synonym of
- SpecIF:isUndirected: true
- SpecIF:Instantiation: user

## SpecIF:isInverseOf (SpecIF:TermStatementClass)
- dcterms:description: A term is the inverse of another term.
  For example, a system 'B' contains a component '11', thus '11' isContainedBy 'B'.
- SpecIF:LifecycleStatus: SpecIF:LifecycleStatusDeprecated
- SpecIF:isUndirected: true

## SpecIF:isAntonymOf (SpecIF:TermStatementClass)
- SpecIF:Revision: 1.2
- dcterms:description: According to Wikipedia, the term antonym (and the related antonymy) is commonly taken to be synonymous with opposite, but antonym also has other more restricted meanings. Graded (or gradable) antonyms are word pairs whose meanings are opposite and which lie on a continuous spectrum (_hot_, _cold_). Complementary antonyms are word pairs whose meanings are opposite but whose meanings do not lie on a continuous spectrum (_push_, _pull_). Relational antonyms are word pairs where opposite makes sense only in the context of the relationship between the two meanings (_teacher_, _pupil_).
- SpecIF:Domain: Ontology
- SpecIF:LifecycleStatus: SpecIF:LifecycleStatusReleased
- SpecIF:LocalTerm: Antonym of
- SpecIF:isUndirected: true
- SpecIF:Instantiation: user

## SpecIF:isPluralOf (SpecIF:TermStatementClass)
- SpecIF:Revision: 1.2
- SpecIF:Domain: Ontology
- SpecIF:LifecycleStatus: SpecIF:LifecycleStatusReleased
- SpecIF:LocalTerm: Plural of
- SpecIF:isUndirected: false
- SpecIF:Instantiation: user

## owl:sameAs (SpecIF:TermStatementClass)
- SpecIF:Revision: 1.2
- dcterms:description: An owl:sameAs statement indicates that two URI references actually refer to the same thing: the individuals have the same 'identity'. (source: OWL)
- SpecIF:Domain: System Model Integration
- SpecIF:LifecycleStatus: SpecIF:LifecycleStatusReleased
- SpecIF:LocalTerm: identical with
- SpecIF:isUndirected: true
- SpecIF:Instantiation: user

## SpecIF:sameAs (SpecIF:TermStatementClass)
- dcterms:description: A resource represents the same entity as another resource.
- SpecIF:LifecycleStatus: SpecIF:LifecycleStatusEquivalent
- SpecIF:isUndirected: true

## SpecIF:isNamespace (SpecIF:TermStatementClass)
- SpecIF:Revision: 1.2
- SpecIF:Domain: Ontology
- SpecIF:LifecycleStatus: SpecIF:LifecycleStatusReleased
- SpecIF:LocalTerm: namespace for
- SpecIF:isUndirected: false

## SpecIF:hasProperty (SpecIF:TermStatementClass)
- SpecIF:Revision: 1.2
- SpecIF:Domain: Ontology
- SpecIF:LifecycleStatus: SpecIF:LifecycleStatusReleased
- SpecIF:LocalTerm: has Property
- SpecIF:isUndirected: false

## SpecIF:hasEnumValue (SpecIF:TermStatementClass)
- SpecIF:Revision: 1.2
- dcterms:description: A property has a data-type 'xs:string' with enumerated value. The value may be an ontology term of a resourcClass, a statementClass or a propertyValue.
  Please note: This holds, if an enumerated value is defined by the ontology. In general, the SpecIF schema allows enumerated values of any data-type. In case of 'xs:string', not only ontology terms, but any string is allowed as value.
- SpecIF:Domain: Ontology
- SpecIF:LifecycleStatus: SpecIF:LifecycleStatusReleased
- SpecIF:LocalTerm: has enumerated Value
- SpecIF:isUndirected: false

## SpecIF:isEligibleAsSubject (SpecIF:TermStatementClass)
- SpecIF:Revision: 1.2
- dcterms:description: A resource-term or statement-term is eligible as a subject of a predicate-term.

  Or concretely: A resource or statement of this class is eligible as the predicate's subject.
- SpecIF:Domain: Ontology
- SpecIF:LifecycleStatus: SpecIF:LifecycleStatusReleased
- SpecIF:LocalTerm: eligible as Subject
- SpecIF:isUndirected: false

## SpecIF:isEligibleAsObject (SpecIF:TermStatementClass)
- SpecIF:Revision: 1.2
- dcterms:description: A resource-term or statement-term is eligible as an object of a predicate-term.

  Or concretely: A resource or statement of this class is eligible as the predicate's object.
- SpecIF:Domain: Ontology
- SpecIF:LifecycleStatus: SpecIF:LifecycleStatusReleased
- SpecIF:LocalTerm: eligible as Object
- SpecIF:isUndirected: false

## DDP:definedBy (SpecIF:TermStatementClass)
- SpecIF:Revision: 1.2
- SpecIF:Domain: System Model Integration
- SpecIF:LocalTerm: defined by
- SpecIF:isUndirected: false
- SpecIF:Instantiation: auto, user

## Property Class Terms (dcterms:title)
- dcterms:description: A property carries information 'payload' and may be applied to resources or statements. The SpecIF terms listed in this chapter are used as property name/title, whereas the information is provided as 'value'. Usually a combination of complimentary properties is used per resource or statement class.
  A property corresponds to an 'ATTRIBUTE-DEFINITION' resp. 'ATTRIBUTE-VALUE' in the Requirements Interchange Format (ReqIF).

## dcterms:identifier (SpecIF:TermPropertyClassString)
- dcterms:identifier: PC-VisibleId
- SpecIF:Revision: 1.1
- dcterms:description: A unique reference to the resource within a given context. (source: DCMI)
  An identifier for a resource. This identifier may be unique with a scope that is defined by the RM provider. Assigned by the service provider when a resource is created. Not intended for end-user display. (source: OSLC)
- SpecIF:LifecycleStatus: SpecIF:LifecycleStatusReleased
- SpecIF:LocalTerm: Identifier
- SpecIF:multiple: false
- SpecIF:multiLanguage: false
- SpecIF:TextFormat: plain

## ReqIF.ForeignID (SpecIF:TermPropertyClassString)
- SpecIF:Revision: 1.2
- dcterms:description: The original identifier of the resource ('object' in terms of ReqIF).
- SpecIF:LocalTerm: Original ID
- SpecIF:Domain: Automotive Stakeholder Request Clarification Process
- SpecIF:LifecycleStatus: SpecIF:LifecycleStatusEquivalent
- SpecIF:multiple: false
- SpecIF:TextFormat: plain
- SpecIF:StringMaxLength: 32

## dcterms:title (SpecIF:TermPropertyClassString)
- dcterms:identifier: PC-Name
- SpecIF:Revision: 1.1
- dcterms:description: A name given to the resource. (source: DCMI)
  Title (reference: Dublin Core) of the resource represented as rich text in XHTML content. SHOULD include only content that is valid inside an XHTML 'span' element. (source: OSLC)
- SpecIF:LocalTerm: Name, Title
- SpecIF:Domain: Base
- SpecIF:LifecycleStatus: SpecIF:LifecycleStatusReleased
- SpecIF:multiple: false
- SpecIF:multiLanguage: true
- SpecIF:TextFormat: plain
- SpecIF:StringMaxLength: 256

## SpecIF:Term (SpecIF:TermPropertyClassString)
- dcterms:identifier: PC-SpecifTerm
- SpecIF:Revision: 1.2
- dcterms:description: A name given to an ontology term.
- SpecIF:Domain: Ontology
- SpecIF:LifecycleStatus: SpecIF:LifecycleStatusReleased
- SpecIF:LocalTerm: Term
- SpecIF:multiple: false
- SpecIF:multiLanguage: false
- SpecIF:TextFormat: plain
- SpecIF:StringMaxLength: 256

## ReqIF.Name (SpecIF:TermPropertyClassString)
- SpecIF:Revision: 1.2
- SpecIF:LocalTerm: Name
- SpecIF:Domain: Base, Automotive Stakeholder Request Clarification Process
- SpecIF:LifecycleStatus: SpecIF:LifecycleStatusEquivalent
- SpecIF:multiple: false
- SpecIF:multiLanguage: true
- SpecIF:TextFormat: xhtml
- SpecIF:StringMaxLength: 256

## ReqIF.ChapterName (SpecIF:TermPropertyClassString)
- SpecIF:Revision: 1.2
- SpecIF:Domain: Automotive Stakeholder Request Clarification Process
- SpecIF:LifecycleStatus: SpecIF:LifecycleStatusSubmitted
- SpecIF:LocalTerm: Chapter Title
- SpecIF:multiple: false
- SpecIF:multiLanguage: false
- SpecIF:TextFormat: xhtml
- SpecIF:StringMaxLength: 256

## ReqIF.ChapterNumber (SpecIF:TermPropertyClassString)
- SpecIF:Revision: 1.2
- SpecIF:Domain: Automotive Stakeholder Request Clarification Process
- SpecIF:LifecycleStatus: SpecIF:LifecycleStatusSubmitted
- SpecIF:LocalTerm: Chapter Number
- SpecIF:multiple: false
- SpecIF:multiLanguage: false
- SpecIF:TextFormat: plain
- SpecIF:StringMaxLength: 32

## dcterms:description (SpecIF:TermPropertyClassString)
- dcterms:identifier: PC-Description
- SpecIF:Revision: 1.1
- dcterms:description: An account of the resource. (source: DCMI)
  Descriptive text (reference: Dublin Core) about resource represented as rich text in XHTML content. SHOULD include only content that is valid and suitable inside an XHTML 'div' element. (source: OSLC)
- SpecIF:LocalTerm: Description
- SpecIF:Domain: Base
- SpecIF:LifecycleStatus: SpecIF:LifecycleStatusReleased
- SpecIF:multiple: false
- SpecIF:multiLanguage: true
- SpecIF:TextFormat: xhtml

## ReqIF.Text (SpecIF:TermPropertyClassString)
- SpecIF:Revision: 1.2
- SpecIF:LocalTerm: Description, Text, Object Text
- SpecIF:Domain: Automotive Stakeholder Request Clarification Process
- SpecIF:LifecycleStatus: SpecIF:LifecycleStatusEquivalent
- SpecIF:multiple: false
- SpecIF:multiLanguage: true
- SpecIF:TextFormat: xhtml

## dcterms:type (SpecIF:TermPropertyClassString)
- dcterms:identifier: PC-Type
- SpecIF:Revision: 1.1
- dcterms:description: The nature or genre of the resource. (source: DCMI)
  Recommended best practice is to use a controlled vocabulary such as the DCMI Type Vocabulary [DCMITYPE]. To describe the file format, physical medium, or dimensions of the resource, use the Format element.
  For example, a [[FMC:Actor]] may represent a System Function, a System Component or a User Role. Similarly, in the context of process modelling, a FMC:Actor may represent a Process Step or again a User Role. So, all of these are meaningful values for a FMC:Actor's property named dcterms:type.
- SpecIF:LocalTerm: Element Type
- SpecIF:Domain: Base
- SpecIF:LifecycleStatus: SpecIF:LifecycleStatusReleased
- SpecIF:multiple: false
- SpecIF:TextFormat: plain
- SpecIF:StringMaxLength: 256

## SpecIF:Type (SpecIF:TermPropertyClassString)
- SpecIF:LifecycleStatus: SpecIF:LifecycleStatusDeprecated
- SpecIF:multiple: false
- SpecIF:multiLanguage: false

## ReqIF.Category (SpecIF:TermPropertyClassString)
- SpecIF:Revision: 1.2
- SpecIF:LocalTerm: Category
- SpecIF:Domain: System Model Integration
- SpecIF:LifecycleStatus: SpecIF:LifecycleStatusEquivalent
- SpecIF:multiple: false
- SpecIF:TextFormat: plain
- SpecIF:StringMaxLength: 256

## SpecIF:Diagram (SpecIF:TermPropertyClassString)
- dcterms:identifier: PC-Diagram
- SpecIF:Revision: 1.1
- dcterms:description: One or more diagrams illustrating the resource.
- SpecIF:LocalTerm: Model Diagram, Diagram, Plan
- SpecIF:Domain: Base, Requirement Engineering, Automotive Stakeholder Request Clarification Process, System Model Integration
- SpecIF:LifecycleStatus: SpecIF:LifecycleStatusReleased
- SpecIF:multiple: true
- SpecIF:TextFormat: xhtml

## SpecIF:Notation (SpecIF:TermPropertyClassString)
- dcterms:identifier: PC-Notation
- SpecIF:Revision: 1.2
- dcterms:description: The notation used by a model diagram, e.g. 'BPMN 2.0', 'SysML Activity Diagram' or 'FMC Block Diagram'.
- SpecIF:Domain: System Model Integration
- SpecIF:LifecycleStatus: SpecIF:LifecycleStatusReleased
- SpecIF:LocalTerm: Notation
- SpecIF:multiple: false
- SpecIF:TextFormat: plain
- SpecIF:StringMaxLength: 32

## SpecIF:Category (SpecIF:TermPropertyClassString)
- dcterms:description: The 'Category' (class) of the resource, usually with an enumerated value.
  Useful categories for requirements have been defined by the IREB, namely 'Function', 'Quality' and 'Constraint'.
- SpecIF:LifecycleStatus: SpecIF:LifecycleStatusEquivalent
- SpecIF:LocalTerm: Category

## SpecIF:Id (SpecIF:TermPropertyClassString)
- dcterms:description: A unique reference to the resource within a given context.
- SpecIF:LifecycleStatus: SpecIF:LifecycleStatusDeprecated

## dcterms:subject (SpecIF:TermPropertyClassString)
- dcterms:description: The topic of the resource. (source: DCMI)
  Tag or keyword for a resource. Each occurrence of a dcterms:subject property denotes an additional tag for the resource. (source: OSLC)
- SpecIF:LifecycleStatus: SpecIF:LifecycleStatusReleased
- SpecIF:LocalTerm: Subject
- SpecIF:multiple: false
- SpecIF:multiLanguage: false

## dcterms:source (SpecIF:TermPropertyClassString)
- dcterms:description: A related resource from which the described resource is derived. (source: DCMI)
  The described resource may be derived from the related resource in whole or in part. Recommended best practice is to identify the related resource by means of a string conforming to a formal identification system.
- SpecIF:LifecycleStatus: SpecIF:LifecycleStatusReleased
- SpecIF:LocalTerm: Source
- SpecIF:multiple: false
- SpecIF:multiLanguage: false
- SpecIF:TextFormat: plain
- SpecIF:StringMaxLength: 32

## dcterms:creator (SpecIF:TermPropertyClassString)
- dcterms:description: An entity primarily responsible for making the resource. (source: DCMI)
  Creator(s) of resource (reference: Dublin Core). It is likely that the target resource will be a [[foaf:Person]] but that is not necessarily the case. (source: OSLC)
- SpecIF:LifecycleStatus: SpecIF:LifecycleStatusReleased
- SpecIF:LocalTerm: created by, Author
- SpecIF:multiple: false
- SpecIF:multiLanguage: false

## SpecIF:createdBy (SpecIF:TermPropertyClassString)
- dcterms:description: A resource primarily responsible for making the resource.
- SpecIF:LifecycleStatus: SpecIF:LifecycleStatusEquivalent

## dcterms:created (SpecIF:TermPropertyClassTimestamp)
- dcterms:description: Timestamp of resource creation. (source: DCMI)
- SpecIF:LifecycleStatus: SpecIF:LifecycleStatusReleased
- SpecIF:LocalTerm: created at
- SpecIF:multiple: false

## SpecIF:createdAt (SpecIF:TermPropertyClassTimestamp)
- dcterms:description: Date/time of creation of the resource.
- SpecIF:LifecycleStatus: SpecIF:LifecycleStatusEquivalent
- SpecIF:LocalTerm: created at
- SpecIF:multiple: false

## SpecIF:changedBy (SpecIF:TermPropertyClassString)
- dcterms:description: The author who made the last modification.
- SpecIF:LocalTerm: changed by
- SpecIF:LifecycleStatus: SpecIF:LifecycleStatusReleased

## dcterms:modified (SpecIF:TermPropertyClassTimestamp)
- dcterms:description: Timestamp last latest resource modification. (source: DCMI)
- SpecIF:LifecycleStatus: SpecIF:LifecycleStatusReleased
- SpecIF:LocalTerm: changed at
- SpecIF:multiple: false

## SpecIF:changedAt (SpecIF:TermPropertyClassTimestamp)
- dcterms:description: Date/time on which the resource was changed last.
- SpecIF:LifecycleStatus: SpecIF:LifecycleStatusEquivalent
- SpecIF:LocalTerm: changed at
- SpecIF:multiple: false

## dcterms:contributor (SpecIF:TermPropertyClassString)
- dcterms:description: A resource responsible for making contributions to the resource. (source: DCMI)
- SpecIF:LifecycleStatus: SpecIF:LifecycleStatusReleased
- SpecIF:LocalTerm: Contributor
- SpecIF:multiple: false
- SpecIF:multiLanguage: false

## dcterms:rightsHolder (SpecIF:TermPropertyClassString)
- dcterms:description: A person or organization owning or managing rights over the resource. (source: DCMI)
- SpecIF:LifecycleStatus: SpecIF:LifecycleStatusReleased
- SpecIF:LocalTerm: Rights Holder

## dcterms:rights (SpecIF:TermPropertyClassString)
- dcterms:description: Information about rights held in and over the resource. (source: DCMI)
- SpecIF:LifecycleStatus: SpecIF:LifecycleStatusReleased
- SpecIF:LocalTerm: Rights

## oslc:shortTitle (SpecIF:TermPropertyClassString)
- dcterms:description: Short name identifying a resource, often used as an abbreviated identifier for presentation to end-users. SHOULD include only content that is valid inside an XHTML 'span' element.

## oslc:serviceProvider (SpecIF:TermPropertyClassString)
- dcterms:description: The scope of a resource is a URI for the resource's OSLC Service Provider.
- SpecIF:Domain: System Model Integration
- SpecIF:LifecycleStatus: SpecIF:LifecycleStatusSubmitted
- SpecIF:LocalTerm: Service Provider
- SpecIF:multiple: false
- SpecIF:multiLanguage: false

## oslc:instanceShape (SpecIF:TermPropertyClassString)
- dcterms:description: Resource Shape that provides hints as to resource property value-types and allowed values.

## SpecIF:Stereotype (SpecIF:TermPropertyClassString)
- dcterms:description: Describes the role or sub-type of a model-element. For example, a [[FMC:Actor]] may represent a System Function, a System Component or a User Role. Similarly, in the context of process modelling, a FMC:Actor may represent a Process Step or again a User Role. So, all of these are meaningful values for a FMC:Actor's property named SpecIF:Stereotype.
- SpecIF:LifecycleStatus: SpecIF:LifecycleStatusDeprecated

## UML:Stereotype (SpecIF:TermPropertyClassString)
- dcterms:description: Describes the role or sub-type of a model-element. For example, a [[FMC:Actor]] may represent a System Function, a System Component or a User Role. Similarly, in the context of process modelling, a FMC:Actor may represent a Process Step or again a User Role. So, all of these are meaningful values for a FMC:Actor's property named UML:Stereotype.
- SpecIF:LocalTerm: Stereotype
- SpecIF:LifecycleStatus: SpecIF:LifecycleStatusReleased

## IREB:RequirementType (SpecIF:TermPropertyClassString)
- dcterms:identifier: PC-RequirementType
- SpecIF:Revision: 1.2
- dcterms:description: According to the IREB, requirements are typically classified into functional requirements ([[IREB:FunctionalRequirement]]), quality requirements ([[IREB:QualityRequirement]]) and constraints ([[IREB:Constraint]]). The latter two are also called non-functional requirements.
- SpecIF:Domain: Requirement Engineering
- SpecIF:LifecycleStatus: SpecIF:LifecycleStatusExperimental
- SpecIF:LocalTerm: Type
- SpecIF:multiple: false
- SpecIF:multiLanguage: false
- SpecIF:TextFormat: plain
- SpecIF:StringMaxLength: 32

## SpecIF:SubClass (SpecIF:TermPropertyClassString)
- dcterms:description: Describes the role or sub-type of a model-element. For example, a [[FMC:Actor]] may represent a System Function, a System Component or a User Role. Similarly, in the context of process modelling, a FMC:Actor may represent a Process Step or again a User Role. So, all of these are meaningful values for a FMC:Actor's property named SpecIF:SubClass.
- SpecIF:LifecycleStatus: SpecIF:LifecycleStatusDeprecated

## SpecIF:LifecycleStatus (SpecIF:TermPropertyClassString)
- dcterms:identifier: PC-LifecycleStatus
- SpecIF:Revision: 1.2
- dcterms:description: The 'Lifecycle Status' of the resource.
- SpecIF:Domain: Base, Requirement Engineering, Automotive Stakeholder Request Clarification Process, System Model Integration
- SpecIF:LifecycleStatus: SpecIF:LifecycleStatusReleased
- SpecIF:LocalTerm: Lifecycle
- SpecIF:multiple: false
- SpecIF:multiLanguage: true
- SpecIF:TextFormat: plain
- SpecIF:StringMaxLength: 32

## SpecIF:Status (SpecIF:TermPropertyClassString)
- dcterms:description: The 'Status' of the resource.
- SpecIF:Domain: Base, Requirement Engineering, Automotive Stakeholder Request Clarification Process, System Model Integration
- SpecIF:LifecycleStatus: SpecIF:LifecycleStatusDeprecated
- SpecIF:LocalTerm: Lifecycle
- SpecIF:multiple: false
- SpecIF:multiLanguage: true
- SpecIF:TextFormat: plain
- SpecIF:StringMaxLength: 32

## SpecIF:TermStatus (SpecIF:TermPropertyClassString)
- dcterms:identifier: PC-TermStatus
- SpecIF:Revision: 1.2
- dcterms:description: The 'status' of the ontology term.
- SpecIF:Domain: Ontology
- SpecIF:LifecycleStatus: SpecIF:LifecycleStatusReleased
- SpecIF:LocalTerm: Lifecycle
- SpecIF:multiple: false
- SpecIF:multiLanguage: true
- SpecIF:TextFormat: plain
- SpecIF:StringMaxLength: 32

## ReqIF.ForeignState (SpecIF:TermPropertyClassString)
- SpecIF:Revision: 1.2
- SpecIF:LocalTerm: Original Status
- dcterms:description: The 'Lifecycle Status' of the resource.
- SpecIF:Domain: Automotive Stakeholder Request Clarification Process
- SpecIF:LifecycleStatus: SpecIF:LifecycleStatusEquivalent
- SpecIF:multiple: false
- SpecIF:TextFormat: plain
- SpecIF:StringMaxLength: 32

## ReqIF.ForeignCreatedBy (SpecIF:TermPropertyClassString)
- SpecIF:Revision: 1.2
- SpecIF:Domain: Automotive Stakeholder Request Clarification Process
- SpecIF:LifecycleStatus: SpecIF:LifecycleStatusEquivalent
- SpecIF:LocalTerm: Author
- SpecIF:multiple: false
- SpecIF:multiLanguage: false
- SpecIF:TextFormat: plain
- SpecIF:StringMaxLength: 32

## ReqIF.ForeignCreatedOn (SpecIF:TermPropertyClassString)
- SpecIF:Revision: 1.2
- SpecIF:Domain: Automotive Stakeholder Request Clarification Process
- SpecIF:LifecycleStatus: SpecIF:LifecycleStatusEquivalent
- SpecIF:LocalTerm: created on
- SpecIF:multiple: false
- SpecIF:multiLanguage: false
- SpecIF:TextFormat: plain
- SpecIF:StringMaxLength: 32

## ReqIF.ForeignCreatedThru (SpecIF:TermPropertyClassString)
- SpecIF:Revision: 1.2
- SpecIF:LocalTerm: created through
- SpecIF:Domain: Automotive Stakeholder Request Clarification Process
- SpecIF:LifecycleStatus: SpecIF:LifecycleStatusExperimental
- SpecIF:multiple: false
- SpecIF:multiLanguage: false
- SpecIF:TextFormat: plain
- SpecIF:StringMaxLength: 32

## ReqIF.ForeignModifiedBy (SpecIF:TermPropertyClassString)
- SpecIF:Revision: 1.2
- SpecIF:Domain: Automotive Stakeholder Request Clarification Process
- SpecIF:LifecycleStatus: SpecIF:LifecycleStatusEquivalent
- SpecIF:LocalTerm: modified by
- SpecIF:multiple: false
- SpecIF:multiLanguage: false
- SpecIF:TextFormat: plain
- SpecIF:StringMaxLength: 32

## ReqIF.ForeignModifiedOn (SpecIF:TermPropertyClassString)
- SpecIF:Revision: 1.2
- SpecIF:Domain: Automotive Stakeholder Request Clarification Process
- SpecIF:LifecycleStatus: SpecIF:LifecycleStatusEquivalent
- SpecIF:LocalTerm: modified on
- SpecIF:multiple: false
- SpecIF:multiLanguage: false
- SpecIF:TextFormat: plain
- SpecIF:StringMaxLength: 32

## ReqIF.Revision (SpecIF:TermPropertyClassString)
- SpecIF:Revision: 1.2
- SpecIF:Domain: Automotive Stakeholder Request Clarification Process
- SpecIF:LifecycleStatus: SpecIF:LifecycleStatusEquivalent
- SpecIF:LocalTerm: Revision
- SpecIF:multiple: false
- SpecIF:multiLanguage: false
- SpecIF:TextFormat: plain
- SpecIF:StringMaxLength: 32

## ReqIF.Prefix (SpecIF:TermPropertyClassString)
- SpecIF:Revision: 1.2
- SpecIF:Domain: Automotive Stakeholder Request Clarification Process
- SpecIF:LifecycleStatus: SpecIF:LifecycleStatusSubmitted
- SpecIF:LocalTerm: Prefix
- SpecIF:multiple: false
- SpecIF:multiLanguage: false
- SpecIF:TextFormat: plain
- SpecIF:StringMaxLength: 32

## ReqIF.Description (SpecIF:TermPropertyClassString)
- SpecIF:Revision: 1.2
- dcterms:description: According to the ReqIF Implementation Guide issued by prostep IVIP, this term is equivalent to ReqIF.Text, but none of the well known authoring tools uses it. Therefore the lifecycle status is set to 'experimental'.
- SpecIF:Domain: Automotive Stakeholder Request Clarification Process
- SpecIF:LifecycleStatus: SpecIF:LifecycleStatusExperimental
- SpecIF:LocalTerm: Description
- SpecIF:multiple: false
- SpecIF:multiLanguage: false
- SpecIF:TextFormat: xhtml

## ReqIF.FitCriteria (SpecIF:TermPropertyClassString)
- SpecIF:Revision: 1.2
- SpecIF:Domain: Automotive Stakeholder Request Clarification Process
- SpecIF:LifecycleStatus: SpecIF:LifecycleStatusEquivalent
- SpecIF:LocalTerm: Fit Criteria
- SpecIF:multiple: false
- SpecIF:multiLanguage: false
- SpecIF:TextFormat: xhtml

## ReqIF.ChangeDescription (SpecIF:TermPropertyClassString)
- SpecIF:Revision: 1.2
- SpecIF:Domain: Automotive Stakeholder Request Clarification Process
- SpecIF:LifecycleStatus: SpecIF:LifecycleStatusSubmitted
- SpecIF:LocalTerm: Change Description
- SpecIF:multiple: false
- SpecIF:multiLanguage: false
- SpecIF:TextFormat: xhtml

## ReqIF.Project (SpecIF:TermPropertyClassString)
- SpecIF:Revision: 1.2
- SpecIF:Domain: Automotive Stakeholder Request Clarification Process
- SpecIF:LifecycleStatus: SpecIF:LifecycleStatusSubmitted
- SpecIF:LocalTerm: Project
- SpecIF:multiple: false
- SpecIF:multiLanguage: false
- SpecIF:TextFormat: xhtml

## ReqIF.AssociatedFiles (SpecIF:TermPropertyClassString)
- SpecIF:Revision: 1.2
- SpecIF:Domain: Automotive Stakeholder Request Clarification Process
- SpecIF:LifecycleStatus: SpecIF:LifecycleStatusSubmitted
- SpecIF:LocalTerm: Attachments
- SpecIF:multiple: false
- SpecIF:multiLanguage: false
- SpecIF:TextFormat: xhtml

## SpecIF:Revision (SpecIF:TermPropertyClassString)
- SpecIF:Revision: 1.2
- SpecIF:Domain: Automotive Stakeholder Request Clarification Process, System Model Integration
- SpecIF:LocalTerm: Revision
- SpecIF:LifecycleStatus: SpecIF:LifecycleStatusReleased
- SpecIF:multiple: false
- SpecIF:multiLanguage: false
- SpecIF:TextFormat: plain
- SpecIF:StringMaxLength: 32

## SpecIF:Domain (SpecIF:TermPropertyClassString)
- SpecIF:Revision: 1.2
- SpecIF:Domain: Ontology
- SpecIF:LifecycleStatus: SpecIF:LifecycleStatusReleased
- SpecIF:LocalTerm: Domain
- SpecIF:multiple: false
- SpecIF:multiLanguage: false
- SpecIF:TextFormat: plain
- SpecIF:StringMaxLength: 32

## SpecIF:LocalTerm (SpecIF:TermPropertyClassString)
- SpecIF:Revision: 1.2
- dcterms:description: A name of the resource used in one or more national languages. Multiple values can be defined so that different local terms can be transformed ('globalized') to the ontology term.
- SpecIF:LocalTerm: Local Term
- SpecIF:Domain: Ontology
- SpecIF:LifecycleStatus: SpecIF:LifecycleStatusReleased
- SpecIF:multiple: true
- SpecIF:multiLanguage: true
- SpecIF:TextFormat: plain
- SpecIF:StringMaxLength: 32

## SpecIF:LocalTermPlural (SpecIF:TermPropertyClassString)
- SpecIF:Revision: 1.2
- dcterms:description: A name of the resource in plural form used in one or more national languages. Multiple values can be defined so that different local terms can be transformed ('globalized') to the ontology term.
- SpecIF:Domain: Ontology
- SpecIF:LifecycleStatus: SpecIF:LifecycleStatusReleased
- SpecIF:LocalTerm: Local Term (Plural)
- SpecIF:multiple: true
- SpecIF:multiLanguage: true
- SpecIF:TextFormat: plain
- SpecIF:StringMaxLength: 32

## SpecIF:Probability (SpecIF:TermPropertyClassReal)
- SpecIF:LifecycleStatus: SpecIF:LifecycleStatusReleased
- SpecIF:LocalTerm: Probability
- SpecIF:multiple: false
- SpecIF:RealMinInclusive: 0
- SpecIF:RealMaxInclusive: 1.0
- SpecIF:RealFractionDigits: 2

## SpecIF:Impact (SpecIF:TermPropertyClassReal)
- SpecIF:Domain: System Model Integration
- SpecIF:LifecycleStatus: SpecIF:LifecycleStatusSubmitted
- SpecIF:LocalTerm: Impact
- SpecIF:multiple: false
- SpecIF:Unit: €
- SpecIF:RealMinInclusive: 0.00
- SpecIF:RealFractionDigits: 2

## SpecIF:Priority (SpecIF:TermPropertyClassString)
- dcterms:identifier: PC-Priority
- SpecIF:Revision: 1.2
- SpecIF:LocalTerm: Priority
- dcterms:description: Enumerated values for the 'Priority' of the resource.
- SpecIF:Domain: Requirement Engineering, Automotive Stakeholder Request Clarification Process, System Model Integration
- SpecIF:LifecycleStatus: SpecIF:LifecycleStatusReleased
- SpecIF:multiple: false
- SpecIF:TextFormat: plain
- SpecIF:StringMaxLength: 32

## SpecIF:Size (SpecIF:TermPropertyClassString)
- SpecIF:Revision: 1.2
- dcterms:description: Enumerated values for the 'Priority' of the resource.
- SpecIF:Domain: Requirement Engineering, Automotive Stakeholder Request Clarification Process, System Model Integration
- SpecIF:LifecycleStatus: SpecIF:LifecycleStatusReleased
- SpecIF:LocalTerm: Size
- SpecIF:multiple: false
- SpecIF:multiLanguage: false
- SpecIF:TextFormat: plain
- SpecIF:StringMaxLength: 32

## SpecIF:Effort (SpecIF:TermPropertyClassString)
- SpecIF:Domain: Requirement Engineering, Automotive Stakeholder Request Clarification Process, System Model Integration
- SpecIF:LifecycleStatus: SpecIF:LifecycleStatusReleased
- SpecIF:LocalTerm: Effort
- SpecIF:multiple: false
- SpecIF:multiLanguage: false
- SpecIF:TextFormat: plain
- SpecIF:StringMaxLength: 32

## SpecIF:Rationale (SpecIF:TermPropertyClassString)
- SpecIF:Domain: Requirement Engineering, Automotive Stakeholder Request Clarification Process, System Model Integration
- SpecIF:LifecycleStatus: SpecIF:LifecycleStatusSubmitted
- SpecIF:LocalTerm: Rationale
- SpecIF:multiple: false
- SpecIF:multiLanguage: false
- SpecIF:TextFormat: plain

## SpecIF:EngineeringDiscipline (SpecIF:TermPropertyClassString)
- dcterms:identifier: PC-Discipline
- SpecIF:Revision: 1.2
- dcterms:description: The engineering discipline involved by a development artefact.
- SpecIF:Domain: Requirement Engineering, Automotive Stakeholder Request Clarification Process, System Model Integration
- SpecIF:LifecycleStatus: SpecIF:LifecycleStatusReleased
- SpecIF:LocalTerm: Engineering Discipline
- SpecIF:multiple: true
- SpecIF:TextFormat: plain
- SpecIF:StringMaxLength: 32

## SpecIF:Discipline (SpecIF:TermPropertyClassString)
- dcterms:description: The engineering discipline involved by a development artefact.
- SpecIF:Domain: Requirement Engineering, Automotive Stakeholder Request Clarification Process, System Model Integration
- SpecIF:LifecycleStatus: SpecIF:LifecycleStatusDeprecated
- SpecIF:LocalTerm: Engineering Discipline
- SpecIF:multiple: true
- SpecIF:multiLanguage: false
- SpecIF:TextFormat: plain
- SpecIF:StringMaxLength: 32

## SpecIF:StakeholderGroup (SpecIF:TermPropertyClassString)
- SpecIF:Revision: 1.2
- dcterms:description: Enumerated values for the 'Stakehoder Group' addressed by the term.
- SpecIF:Domain: Requirement Engineering, Automotive Stakeholder Request Clarification Process, System Model Integration
- SpecIF:LifecycleStatus: SpecIF:LifecycleStatusReleased
- SpecIF:LocalTerm: Stakeholder Group
- SpecIF:multiple: false
- SpecIF:TextFormat: plain
- SpecIF:StringMaxLength: 32

## SpecIF:Perspective (SpecIF:TermPropertyClassString)
- dcterms:identifier: PC-Perspective
- SpecIF:Revision: 1.2
- dcterms:description: Enumerated values for the perspective (of a requirement).
- SpecIF:Domain: Requirement Engineering, Automotive Stakeholder Request Clarification Process, System Model Integration
- SpecIF:LifecycleStatus: SpecIF:LifecycleStatusDeprecated
- SpecIF:LocalTerm: Perspective
- SpecIF:multiple: false
- SpecIF:multiLanguage: false
- SpecIF:TextFormat: plain
- SpecIF:StringMaxLength: 32

## SpecIF:Responsible (SpecIF:TermPropertyClassString)
- dcterms:description: The 'Person' being responsible for the resource.
- SpecIF:LifecycleStatus: SpecIF:LifecycleStatusReleased
- SpecIF:LocalTerm: Responsible

## SpecIF:Accountable (SpecIF:TermPropertyClassString)
- dcterms:description: The 'Person' being accountable for the resource.
- SpecIF:LifecycleStatus: SpecIF:LifecycleStatusReleased
- SpecIF:LocalTerm: Accountable
- SpecIF:multiple: false
- SpecIF:multiLanguage: false

## SpecIF:Milestone (SpecIF:TermPropertyClassTimestamp)
- dcterms:description: A target 'Milestone' to implement the resource.
- SpecIF:LifecycleStatus: SpecIF:LifecycleStatusReleased
- SpecIF:LocalTerm: Milestone

## SpecIF:DueDate (SpecIF:TermPropertyClassTimestamp)
- dcterms:description: A 'Due Date' for the resource.
- SpecIF:LifecycleStatus: SpecIF:LifecycleStatusReleased
- SpecIF:LocalTerm: Due Date

## SpecIF:Benefit (SpecIF:TermPropertyClassString)
- SpecIF:LifecycleStatus: SpecIF:LifecycleStatusReleased
- SpecIF:LocalTerm: Benefit
- SpecIF:multiple: false
- SpecIF:multiLanguage: true
- SpecIF:TextFormat: plain

## SpecIF:Damage (SpecIF:TermPropertyClassString)
- SpecIF:LifecycleStatus: SpecIF:LifecycleStatusReleased
- SpecIF:LocalTerm: Damage
- SpecIF:multiple: false
- SpecIF:multiLanguage: true
- SpecIF:TextFormat: plain

## SpecIF:Icon (SpecIF:TermPropertyClassString)
- SpecIF:Revision: 1.2
- dcterms:description: An icon associated with the resource class.
- SpecIF:LifecycleStatus: SpecIF:LifecycleStatusReleased
- SpecIF:LocalTerm: Icon
- SpecIF:multiple: false
- SpecIF:multiLanguage: false

## SpecIF:Unit (SpecIF:TermPropertyClassString)
- SpecIF:Revision: 1.2
- dcterms:description: The unit of a property's numeric value; preferably an SI unit symbol such as 'm^3/kg' (Système international (d'unités)) or a currency symbol.
- SpecIF:Domain: System Model Integration
- SpecIF:LifecycleStatus: SpecIF:LifecycleStatusReleased
- SpecIF:LocalTerm: Unit
- SpecIF:multiple: false
- SpecIF:multiLanguage: false
- SpecIF:TextFormat: plain
- SpecIF:StringMaxLength: 32

## SpecIF:Tag (SpecIF:TermPropertyClassString)
- SpecIF:LifecycleStatus: SpecIF:LifecycleStatusReleased
- SpecIF:LocalTerm: Tag
- SpecIF:multiple: true
- SpecIF:multiLanguage: true
- SpecIF:TextFormat: plain
- SpecIF:StringMaxLength: 32

## SpecIF:Instantiation (SpecIF:TermPropertyClassString)
- dcterms:description: 'user': a user creates, updates and deletes a resource's instance manually.
  'auto': a resource's instance is created, updated or deleted by an algorithm.
- SpecIF:LifecycleStatus: SpecIF:LifecycleStatusReleased
- SpecIF:LocalTerm: Instantiation
- SpecIF:multiple: false
- SpecIF:multiLanguage: false

## SpecIF:Creation (SpecIF:TermPropertyClassString)
- dcterms:description: 'manual': user interface supports creation, update and deletion of the resource.
  'auto': the resource is created, updated or deleted by an algorithm.
- SpecIF:LifecycleStatus: SpecIF:LifecycleStatusDeprecated
- SpecIF:multiple: false
- SpecIF:multiLanguage: false

## SpecIF:Origin (SpecIF:TermPropertyClassString)
- dcterms:description: The origin (source, reference) of an information or requirement
- SpecIF:LifecycleStatus: SpecIF:LifecycleStatusReleased
- SpecIF:LocalTerm: Origin

## SpecIF:Subject (SpecIF:TermPropertyClassString)
- dcterms:description: The subject of a subject-predicate-object statement. Corresponds to a 'source' in ReqIF terminology.
- SpecIF:LifecycleStatus: SpecIF:LifecycleStatusReleased
- SpecIF:LocalTerm: Subject

## SpecIF:Source (SpecIF:TermPropertyClassString)
- dcterms:description: The subject of a subject-predicate-object statement.
- SpecIF:LifecycleStatus: SpecIF:LifecycleStatusDeprecated
- SpecIF:LocalTerm: Source

## SpecIF:Object (SpecIF:TermPropertyClassString)
- dcterms:description: The object of a subject-predicate-object statement. Corresponds to a 'target' in ReqIF terminology.
- SpecIF:LifecycleStatus: SpecIF:LifecycleStatusReleased
- SpecIF:LocalTerm: Object

## SpecIF:Target (SpecIF:TermPropertyClassString)
- dcterms:description: The object of a subject-predicate-object statement.
- SpecIF:LifecycleStatus: SpecIF:LifecycleStatusDeprecated
- SpecIF:LocalTerm: Target

## SpecIF:FitCriteria (SpecIF:TermPropertyClassString)
- SpecIF:LifecycleStatus: SpecIF:LifecycleStatusReleased
- SpecIF:LocalTerm: Fit Criteria

## SpecIF:OrdinalMark (SpecIF:TermPropertyClassString)
- dcterms:description: A string to determine the ordering of elements. Rules:
  - For ordering, only alphanumeric characters are permissible. A letter case has no effect; for example, 'F' is equivalent to 'f'.
  - The ordering at character level is alphanumeric, i.e. '1' < '7' < 'D' < 'X'.
  - Single character substrings < two-character substrings < substrings with more characters, thus '9' < '12' < '114'.
  - The ordinal mark may be separated by non-alphanumeric characters. All separators are equivalent; e.g. '-' is equivalent to ';' or '/'.
  - Each alphanumeric substring is used for ordering on its hierarchical level; the leftmost substring is most significant for the overall ordering.
  - For example '1' < '1.2' < '1.Y' < '1.1a' < '1-1b' < '1-1C' < '2'.
  A regular expression for extracting the substrings of an ordinal mark is /([0-9a-z]+)[^0-9a-z]{0,1}/gi.
- SpecIF:LifecycleStatus: SpecIF:LifecycleStatusExperimental
- SpecIF:LocalTerm: Ordinal Mark

## SpecIF:multiple (SpecIF:TermPropertyClassBoolean)
- SpecIF:Revision: 1.2
- dcterms:description: The property may have multiple values.
- SpecIF:Domain: Ontology
- SpecIF:LifecycleStatus: SpecIF:LifecycleStatusReleased
- SpecIF:LocalTerm: multiple values
- SpecIF:multiple: false
- SpecIF:DefaultValue: false

## SpecIF:multiLanguage (SpecIF:TermPropertyClassBoolean)
- SpecIF:Revision: 1.2
- dcterms:description: A property value may have multiple languages.
- SpecIF:Domain: Ontology
- SpecIF:LifecycleStatus: SpecIF:LifecycleStatusReleased
- SpecIF:LocalTerm: multi-language
- SpecIF:multiple: false
- SpecIF:DefaultValue: false

## SpecIF:isHeading (SpecIF:TermPropertyClassBoolean)
- SpecIF:Revision: 1.2
- dcterms:description: Indicates whether the resource is a heading, e.g. for adding automatic numbering or influencing the display size.
- SpecIF:Domain: Ontology
- SpecIF:LifecycleStatus: SpecIF:LifecycleStatusReleased
- SpecIF:LocalTerm: Heading
- SpecIF:multiple: false
- SpecIF:DefaultValue: false

## SpecIF:isUndirected (SpecIF:TermPropertyClassBoolean)
- SpecIF:Revision: 1.2
- dcterms:description: Indicates whether the statement is undirected, i.e. whether is can be reversed without change in meaning. A typical example is [[SpecIF:isSynonymOf]].
- SpecIF:Domain: Ontology
- SpecIF:LifecycleStatus: SpecIF:LifecycleStatusReleased
- SpecIF:LocalTerm: undirected
- SpecIF:multiple: false
- SpecIF:DefaultValue: false

## SpecIF:DefaultValue (SpecIF:TermPropertyClassString)
- SpecIF:Revision: 1.2
- SpecIF:Domain: Ontology
- SpecIF:LifecycleStatus: SpecIF:LifecycleStatusReleased
- SpecIF:LocalTerm: Default Value
- SpecIF:multiple: true
- SpecIF:multiLanguage: false
- SpecIF:TextFormat: plain

## SpecIF:DefaultValueString (SpecIF:TermPropertyClassString)
- SpecIF:Revision: 1.2
- SpecIF:Domain: Ontology
- SpecIF:LifecycleStatus: SpecIF:LifecycleStatusReleased
- SpecIF:LocalTerm: Default Value
- SpecIF:multiple: true
- SpecIF:multiLanguage: true
- SpecIF:TextFormat: xhtml

## SpecIF:TextFormat (SpecIF:TermPropertyClassString)
- SpecIF:Revision: 1.2
- dcterms:description: The type of formatting, plain or XHTML.
- SpecIF:Domain: Ontology
- SpecIF:LifecycleStatus: SpecIF:LifecycleStatusReleased
- SpecIF:LocalTerm: Text format
- SpecIF:multiple: false
- SpecIF:multiLanguage: false
- SpecIF:TextFormat: plain
- SpecIF:StringMaxLength: 32

## SpecIF:StringMaxLength (SpecIF:TermPropertyClassInteger)
- SpecIF:Revision: 1.2
- dcterms:description: Maximum length of a string value.
- SpecIF:Domain: Ontology
- SpecIF:LifecycleStatus: SpecIF:LifecycleStatusReleased
- SpecIF:LocalTerm: max. Length
- SpecIF:multiple: false

## SpecIF:IntegerMinInclusive (SpecIF:TermPropertyClassInteger)
- SpecIF:Revision: 1.2
- dcterms:description: Inclusive minimum of an integer value.
- SpecIF:Domain: Ontology
- SpecIF:LifecycleStatus: SpecIF:LifecycleStatusReleased
- SpecIF:LocalTerm: min. Value
- SpecIF:multiple: false
- SpecIF:IntegerMinInclusive: -2147483648
- SpecIF:IntegerMaxInclusive: 2147483647

## SpecIF:IntegerMaxInclusive (SpecIF:TermPropertyClassInteger)
- SpecIF:Revision: 1.2
- dcterms:description: Inclusive maximum of an integer value.
- SpecIF:Domain: Ontology
- SpecIF:LifecycleStatus: SpecIF:LifecycleStatusReleased
- SpecIF:LocalTerm: max. Value
- SpecIF:multiple: false
- SpecIF:IntegerMinInclusive: -2147483648
- SpecIF:IntegerMaxInclusive: 2147483647

## SpecIF:RealMinInclusive (SpecIF:TermPropertyClassReal)
- SpecIF:Revision: 1.2
- dcterms:description: Inclusive minimum of a real value.
- SpecIF:Domain: Ontology
- SpecIF:LocalTerm: min. Value
- SpecIF:multiple: false

## SpecIF:RealMaxInclusive (SpecIF:TermPropertyClassReal)
- SpecIF:Revision: 1.2
- dcterms:description: Inclusive maximum of a real value.
- SpecIF:Domain: Ontology
- SpecIF:LocalTerm: max. Value
- SpecIF:multiple: false

## SpecIF:RealFractionDigits (SpecIF:TermPropertyClassInteger)
- SpecIF:Revision: 1.2
- dcterms:description: Max. count of decimals of a real number.
- SpecIF:Domain: Ontology
- SpecIF:LocalTerm: Decimals
- SpecIF:multiple: false
- SpecIF:DefaultValue: 2
- SpecIF:IntegerMinInclusive: 0

## ReqIF-WF.CustomerStatus (SpecIF:TermPropertyClassString)
- dcterms:identifier: PC-CustomerStatus
- SpecIF:Revision: 1.2
- SpecIF:Domain: Automotive Stakeholder Request Clarification Process
- SpecIF:LifecycleStatus: SpecIF:LifecycleStatusReleased
- SpecIF:LocalTerm: Customer Status
- SpecIF:multiple: false
- SpecIF:multiLanguage: false
- SpecIF:TextFormat: plain
- SpecIF:StringMaxLength: 32

## ReqIF-WF.CustomerComment (SpecIF:TermPropertyClassString)
- dcterms:identifier: PC-CustomerComment
- SpecIF:Revision: 1.2
- SpecIF:Domain: Automotive Stakeholder Request Clarification Process
- SpecIF:LifecycleStatus: SpecIF:LifecycleStatusReleased
- SpecIF:LocalTerm: Customer Comment
- SpecIF:multiple: true
- SpecIF:multiLanguage: false
- SpecIF:TextFormat: xhtml

## ReqIF-WF.SupplierStatus (SpecIF:TermPropertyClassString)
- dcterms:identifier: PC-SupplierStatus
- SpecIF:Revision: 1.2
- SpecIF:Domain: Automotive Stakeholder Request Clarification Process
- SpecIF:LifecycleStatus: SpecIF:LifecycleStatusReleased
- SpecIF:LocalTerm: Supplier Status
- SpecIF:multiple: false
- SpecIF:multiLanguage: false
- SpecIF:TextFormat: plain
- SpecIF:StringMaxLength: 32

## ReqIF-WF.SupplierComment (SpecIF:TermPropertyClassString)
- dcterms:identifier: PC-SupplierComment
- SpecIF:Revision: 1.2
- SpecIF:Domain: Automotive Stakeholder Request Clarification Process
- SpecIF:LifecycleStatus: SpecIF:LifecycleStatusReleased
- SpecIF:LocalTerm: Supplier Comment
- SpecIF:multiple: true
- SpecIF:multiLanguage: false
- SpecIF:TextFormat: xhtml

## HIS:OemStatus (SpecIF:TermPropertyClassString)
- SpecIF:Domain: Automotive Stakeholder Request Clarification Process
- SpecIF:LifecycleStatus: SpecIF:LifecycleStatusEquivalent

## HIS:OemComment (SpecIF:TermPropertyClassString)
- SpecIF:Domain: Automotive Stakeholder Request Clarification Process
- SpecIF:LifecycleStatus: SpecIF:LifecycleStatusEquivalent

## HIS:SupplierComment (SpecIF:TermPropertyClassString)
- SpecIF:Domain: Automotive Stakeholder Request Clarification Process
- SpecIF:LifecycleStatus: SpecIF:LifecycleStatusEquivalent

## HIS:SupplierStatus (SpecIF:TermPropertyClassString)
- SpecIF:Domain: Automotive Stakeholder Request Clarification Process
- SpecIF:LifecycleStatus: SpecIF:LifecycleStatusEquivalent

## SpecIF:ModelFile (SpecIF:TermPropertyClassString)
- SpecIF:Revision: 1.2
- dcterms:description: A file with partial model information.
- SpecIF:Domain: Requirement Engineering, Automotive Stakeholder Request Clarification Process, System Model Integration
- SpecIF:LifecycleStatus: SpecIF:LifecycleStatusSubmitted
- SpecIF:LocalTerm: Model File
- SpecIF:multiple: false
- SpecIF:multiLanguage: false
- SpecIF:TextFormat: xhtml
- SpecIF:StringMaxLength: 256

## Property Value Terms (dcterms:title)
- dcterms:description: These are terms for certain enumerated property values. Not only the property titles, but also any enumerated value must be mapped between different systems or domains; therefore using defined terms is beneficial. Of course, like any other vocabulary term, a term used as property value for transmission or storage can be translated for display.

## SpecIF:priorityHigh (SpecIF:TermPropertyValue)
- dcterms:description: A value for property [[SpecIF:Priority]].
- SpecIF:LocalTerm: high
- SpecIF:Domain: Requirement Engineering, Automotive Stakeholder Request Clarification Process, System Model Integration
- SpecIF:LifecycleStatus: SpecIF:LifecycleStatusReleased

## SpecIF:priorityRatherHigh (SpecIF:TermPropertyValue)
- dcterms:description: A value for property [[SpecIF:Priority]].
- SpecIF:LocalTerm: rather high
- SpecIF:Domain: Requirement Engineering, Automotive Stakeholder Request Clarification Process, System Model Integration
- SpecIF:LifecycleStatus: SpecIF:LifecycleStatusReleased

## SpecIF:priorityMedium (SpecIF:TermPropertyValue)
- dcterms:description: A value for property [[SpecIF:Priority]].
- SpecIF:LocalTerm: medium
- SpecIF:Domain: Requirement Engineering, Automotive Stakeholder Request Clarification Process, System Model Integration
- SpecIF:LifecycleStatus: SpecIF:LifecycleStatusReleased

## SpecIF:priorityRatherLow (SpecIF:TermPropertyValue)
- dcterms:description: A value for property [[SpecIF:Priority]].
- SpecIF:LocalTerm: rather low
- SpecIF:Domain: Requirement Engineering, Automotive Stakeholder Request Clarification Process, System Model Integration
- SpecIF:LifecycleStatus: SpecIF:LifecycleStatusReleased

## SpecIF:priorityLow (SpecIF:TermPropertyValue)
- dcterms:description: A value for property [[SpecIF:Priority]].
- SpecIF:LocalTerm: low
- SpecIF:Domain: Requirement Engineering, Automotive Stakeholder Request Clarification Process, System Model Integration
- SpecIF:LifecycleStatus: SpecIF:LifecycleStatusReleased

## SpecIF:sizeXL (SpecIF:TermPropertyValue)
- dcterms:description: T-shirt sizes have become popular to classify [[IREB:Risk]], [[SpecIF:Damage]] or similar. Translates to 'very large' in English.
- SpecIF:LifecycleStatus: SpecIF:LifecycleStatusExperimental
- SpecIF:LocalTerm: XL, very big

## SpecIF:sizeL (SpecIF:TermPropertyValue)
- dcterms:description: T-shirt sizes have become popular to classify [[IREB:Risk]], [[SpecIF:Damage]] or similar. Translates to 'large' in English.
- SpecIF:LifecycleStatus: SpecIF:LifecycleStatusExperimental
- SpecIF:LocalTerm: L, big

## SpecIF:sizeM (SpecIF:TermPropertyValue)
- dcterms:description: T-shirt sizes have become popular to classify [[IREB:Risk]], [[SpecIF:Damage]] or similar. Translates to 'medium' in English.
- SpecIF:LifecycleStatus: SpecIF:LifecycleStatusExperimental
- SpecIF:LocalTerm: M, medium

## SpecIF:sizeS (SpecIF:TermPropertyValue)
- dcterms:description: T-shirt sizes have become popular to classify [[IREB:Risk]], [[SpecIF:Damage]] or similar. Translates to 'small' in English.
- SpecIF:LifecycleStatus: SpecIF:LifecycleStatusExperimental
- SpecIF:LocalTerm: S, small

## SpecIF:sizeXS (SpecIF:TermPropertyValue)
- dcterms:description: T-shirt sizes have become popular to classify [[IREB:Risk]], [[SpecIF:Damage]] or similar. Translates to 'very small' in English.
- SpecIF:LifecycleStatus: SpecIF:LifecycleStatusExperimental
- SpecIF:LocalTerm: XS, very small

## SpecIF:LifecycleStatusInitial (SpecIF:TermPropertyValue)
- SpecIF:LifecycleStatus: SpecIF:LifecycleStatusSubmitted
- SpecIF:LocalTerm: initial, 10_initial

## SpecIF:LifecycleStatusDrafted (SpecIF:TermPropertyValue)
- SpecIF:LifecycleStatus: SpecIF:LifecycleStatusSubmitted
- SpecIF:LocalTerm: drafted, 20_drafted

## SpecIF:LifecycleStatusSubmitted (SpecIF:TermPropertyValue)
- SpecIF:LocalTerm: submitted, 30_submitted

## SpecIF:LifecycleStatusApproved (SpecIF:TermPropertyValue)
- SpecIF:LifecycleStatus: SpecIF:LifecycleStatusSubmitted
- SpecIF:LocalTerm: approved, 40_approved

## SpecIF:LifecycleStatusReady (SpecIF:TermPropertyValue)
- dcterms:description: Meets the requirements of the 'Definition of Ready' of the agile development method.
- SpecIF:LifecycleStatus: SpecIF:LifecycleStatusSubmitted
- SpecIF:LocalTerm: ready

## SpecIF:LifecycleStatusDone (SpecIF:TermPropertyValue)
- dcterms:description: Meets the requirements of the 'Definition of Done' of the agile development method.
- SpecIF:LifecycleStatus: SpecIF:LifecycleStatusSubmitted
- SpecIF:LocalTerm: done, 60_completed

## SpecIF:LifecycleStatusValidated (SpecIF:TermPropertyValue)
- SpecIF:LifecycleStatus: SpecIF:LifecycleStatusSubmitted
- SpecIF:LocalTerm: validated, 70_validated, 70_tested

## SpecIF:LifecycleStatusReleased (SpecIF:TermPropertyValue)
- SpecIF:LifecycleStatus: SpecIF:LifecycleStatusSubmitted
- SpecIF:LocalTerm: released, 80_released, published

## SpecIF:LifecycleStatusDeprecated (SpecIF:TermPropertyValue)
- SpecIF:LifecycleStatus: SpecIF:LifecycleStatusSubmitted
- SpecIF:LocalTerm: deprecated, 00_deprecated

## SpecIF:LifecycleStatusWithdrawn (SpecIF:TermPropertyValue)
- SpecIF:LifecycleStatus: SpecIF:LifecycleStatusSubmitted
- SpecIF:LocalTerm: withdrawn, 90_withdrawn

## SpecIF:LifecycleStatusPostponed (SpecIF:TermPropertyValue)
- SpecIF:LifecycleStatus: SpecIF:LifecycleStatusSubmitted
- SpecIF:LocalTerm: postponed, 00_postponed

## SpecIF:LifecycleStatusRejected (SpecIF:TermPropertyValue)
- SpecIF:LifecycleStatus: SpecIF:LifecycleStatusSubmitted
- SpecIF:LocalTerm: rejected, 00_rejected

## SpecIF:LifecycleStatusExperimental (SpecIF:TermPropertyValue)
- SpecIF:Domain: Ontology
- SpecIF:LifecycleStatus: SpecIF:LifecycleStatusSubmitted
- SpecIF:LocalTerm: experimental

## SpecIF:LifecycleStatusEquivalent (SpecIF:TermPropertyValue)
- SpecIF:Domain: Ontology
- SpecIF:LifecycleStatus: SpecIF:LifecycleStatusSubmitted
- SpecIF:LocalTerm: equivalent

## SpecIF:EngineeringDisciplineMechanics (SpecIF:TermPropertyValue)
- SpecIF:Revision: 1.2
- SpecIF:Domain: Requirement Engineering, Automotive Stakeholder Request Clarification Process, System Model Integration
- SpecIF:LifecycleStatus: SpecIF:LifecycleStatusReleased
- SpecIF:LocalTerm: Mechanics

## SpecIF:EngineeringDisciplineElectronics (SpecIF:TermPropertyValue)
- SpecIF:Revision: 1.2
- SpecIF:Domain: Requirement Engineering, Automotive Stakeholder Request Clarification Process, System Model Integration
- SpecIF:LifecycleStatus: SpecIF:LifecycleStatusReleased
- SpecIF:LocalTerm: Electronics

## SpecIF:EngineeringDisciplineSoftware (SpecIF:TermPropertyValue)
- SpecIF:Revision: 1.2
- SpecIF:Domain: Requirement Engineering, Automotive Stakeholder Request Clarification Process, System Model Integration
- SpecIF:LifecycleStatus: SpecIF:LifecycleStatusReleased
- SpecIF:LocalTerm: Software

## SpecIF:EngineeringDisciplineSafety (SpecIF:TermPropertyValue)
- SpecIF:Revision: 1.2
- SpecIF:Domain: Requirement Engineering, Automotive Stakeholder Request Clarification Process, System Model Integration
- SpecIF:LifecycleStatus: SpecIF:LifecycleStatusReleased
- SpecIF:LocalTerm: Safety

## SpecIF:EngineeringDisciplineSystem (SpecIF:TermPropertyValue)
- SpecIF:Revision: 1.2
- SpecIF:Domain: Requirement Engineering, Automotive Stakeholder Request Clarification Process, System Model Integration
- SpecIF:LifecycleStatus: SpecIF:LifecycleStatusReleased
- SpecIF:LocalTerm: System Engineering

## SpecIF:StakeholderGroupRegulation (SpecIF:TermPropertyValue)
- SpecIF:Revision: 1.2
- dcterms:description: A 'Stakeholder Group' addressed by a requirement.
- SpecIF:Domain: Requirement Engineering, Automotive Stakeholder Request Clarification Process, System Model Integration
- SpecIF:LifecycleStatus: SpecIF:LifecycleStatusReleased
- SpecIF:LocalTerm: Regulation

## SpecIF:StakeholderGroupBusiness (SpecIF:TermPropertyValue)
- SpecIF:Revision: 1.2
- dcterms:description: A 'Stakeholder Group' addressed by a requirement.
- SpecIF:Domain: Requirement Engineering, Automotive Stakeholder Request Clarification Process, System Model Integration
- SpecIF:LifecycleStatus: SpecIF:LifecycleStatusReleased
- SpecIF:LocalTerm: Business

## SpecIF:StakeholderGroupUser (SpecIF:TermPropertyValue)
- SpecIF:Revision: 1.2
- dcterms:description: A 'Stakeholder Group' addressed by a requirement.
- SpecIF:Domain: Requirement Engineering, Automotive Stakeholder Request Clarification Process, System Model Integration
- SpecIF:LifecycleStatus: SpecIF:LifecycleStatusReleased
- SpecIF:LocalTerm: User

## SpecIF:StakeholderGroupOperation (SpecIF:TermPropertyValue)
- SpecIF:Revision: 1.2
- dcterms:description: A 'Stakeholder Group' addressed by a requirement.
- SpecIF:Domain: Requirement Engineering, Automotive Stakeholder Request Clarification Process, System Model Integration
- SpecIF:LifecycleStatus: SpecIF:LifecycleStatusReleased
- SpecIF:LocalTerm: Operation

## IREB:RequirementTypeFunction (SpecIF:TermPropertyValue)
- dcterms:description: A requirement concerning a result of behavior that shall be provided by a function of a system (or of a component or service).
- SpecIF:LifecycleStatus: SpecIF:LifecycleStatusEquivalent
- SpecIF:LocalTerm: Function or User Story

## IREB:RequirementTypeQuality (SpecIF:TermPropertyValue)
- dcterms:description: A [[IREB:Requirement]] that pertains to a quality concern that is not covered by functional requirements.
- SpecIF:LifecycleStatus: SpecIF:LifecycleStatusEquivalent
- SpecIF:LocalTerm: Quality

## IREB:RequirementTypeConstraint (SpecIF:TermPropertyValue)
- dcterms:description: A [[IREB:Requirement]] that limits the solution space beyond what is necessary for meeting the given functional requirements and quality requirements.
- SpecIF:LifecycleStatus: SpecIF:LifecycleStatusEquivalent
- SpecIF:LocalTerm: Constraint

## IREB:FunctionalRequirement (SpecIF:TermPropertyValue)
- SpecIF:Revision: 1.2
- dcterms:description: A [[IREB:Requirement]] concerning a result of behavior that shall be provided by a function of a system (or of a component or service).
- SpecIF:Domain: Requirement Engineering, Automotive Stakeholder Request Clarification Process
- SpecIF:LifecycleStatus: SpecIF:LifecycleStatusReleased
- SpecIF:LocalTerm: Functional Requirement or 'User Story'

## IREB:QualityRequirement (SpecIF:TermPropertyValue)
- SpecIF:Revision: 1.2
- dcterms:description: A [[IREB:Requirement]] that pertains to a quality concern that is not covered by functional requirements.
- SpecIF:Domain: Requirement Engineering, Automotive Stakeholder Request Clarification Process
- SpecIF:LifecycleStatus: SpecIF:LifecycleStatusReleased
- SpecIF:LocalTerm: Quality Requirement

## IREB:Constraint (SpecIF:TermPropertyValue)
- SpecIF:Revision: 1.2
- dcterms:description: A [[IREB:Requirement]] that limits the solution space beyond what is necessary for meeting the given functional requirements and quality requirements.
- SpecIF:Domain: Requirement Engineering, Automotive Stakeholder Request Clarification Process
- SpecIF:LifecycleStatus: SpecIF:LifecycleStatusReleased
- SpecIF:LocalTerm: Constraint

## SpecIF:PerspectiveBusiness (SpecIF:TermPropertyValue)
- SpecIF:Revision: 1.2
- SpecIF:Domain: Requirement Engineering, Automotive Stakeholder Request Clarification Process
- SpecIF:LifecycleStatus: SpecIF:LifecycleStatusReleased
- SpecIF:LocalTerm: Business

## SpecIF:PerspectiveStakeholder (SpecIF:TermPropertyValue)
- SpecIF:Revision: 1.2
- SpecIF:Domain: Requirement Engineering, Automotive Stakeholder Request Clarification Process
- SpecIF:LifecycleStatus: SpecIF:LifecycleStatusReleased
- SpecIF:LocalTerm: Stakeholder

## SpecIF:PerspectiveUser (SpecIF:TermPropertyValue)
- SpecIF:Revision: 1.2
- SpecIF:Domain: Requirement Engineering, Automotive Stakeholder Request Clarification Process
- SpecIF:LifecycleStatus: SpecIF:LifecycleStatusReleased
- SpecIF:LocalTerm: User

## SpecIF:PerspectiveOperator (SpecIF:TermPropertyValue)
- SpecIF:Revision: 1.2
- SpecIF:Domain: Requirement Engineering, Automotive Stakeholder Request Clarification Process
- SpecIF:LifecycleStatus: SpecIF:LifecycleStatusReleased
- SpecIF:LocalTerm: Operator

## SpecIF:PerspectiveSystem (SpecIF:TermPropertyValue)
- SpecIF:Revision: 1.2
- SpecIF:Domain: Requirement Engineering, Automotive Stakeholder Request Clarification Process
- SpecIF:LifecycleStatus: SpecIF:LifecycleStatusReleased
- SpecIF:LocalTerm: System

## SpecIF:DisciplineSystem (SpecIF:TermPropertyValue)
- SpecIF:Domain: Requirement Engineering, Automotive Stakeholder Request Clarification Process
- SpecIF:LifecycleStatus: SpecIF:LifecycleStatusDeprecated
- SpecIF:LocalTerm: System

## SpecIF:DisciplineSystemEngineering (SpecIF:TermPropertyValue)
- SpecIF:Domain: Requirement Engineering, Automotive Stakeholder Request Clarification Process
- SpecIF:LifecycleStatus: SpecIF:LifecycleStatusDeprecated
- SpecIF:LocalTerm: System

## SpecIF:DisciplineMechanics (SpecIF:TermPropertyValue)
- SpecIF:Domain: Requirement Engineering, Automotive Stakeholder Request Clarification Process
- SpecIF:LifecycleStatus: SpecIF:LifecycleStatusDeprecated
- SpecIF:LocalTerm: Mechanics

## SpecIF:DisciplineElectronics (SpecIF:TermPropertyValue)
- SpecIF:Domain: Requirement Engineering, Automotive Stakeholder Request Clarification Process
- SpecIF:LifecycleStatus: SpecIF:LifecycleStatusDeprecated
- SpecIF:LocalTerm: Electronics

## SpecIF:DisciplineSoftware (SpecIF:TermPropertyValue)
- SpecIF:Domain: Requirement Engineering, Automotive Stakeholder Request Clarification Process
- SpecIF:LifecycleStatus: SpecIF:LifecycleStatusDeprecated
- SpecIF:LocalTerm: Software

## SpecIF:DisciplineSafety (SpecIF:TermPropertyValue)
- SpecIF:Domain: Requirement Engineering, Automotive Stakeholder Request Clarification Process
- SpecIF:LifecycleStatus: SpecIF:LifecycleStatusDeprecated
- SpecIF:LocalTerm: Safety

## SpecIF:NotApplicable (SpecIF:TermPropertyValue)
- SpecIF:Domain: Automotive Stakeholder Request Clarification Process
- SpecIF:LifecycleStatus: SpecIF:LifecycleStatusReleased
- SpecIF:LocalTerm: not applicable, not-applicable, n/a

## ReqIF-WF.CustomerStatus.NotToEvaluate (SpecIF:TermPropertyValue)
- dcterms:description: The requirement is relevant, but no evaluation is expected.
  - Attribute can be set to this value during the first transmission
  - Attribute can be changed to this value during the assessment process to indicate that a requirement must no longer be evaluated
  - Supplier can react with [[ReqIF-WF.SupplierStatus.ToBeClarified]] if he has objections to the non-evaluation. Otherwise, the SupplierStatus remains empty and the workflow ends.
- SpecIF:Domain: Automotive Stakeholder Request Clarification Process
- SpecIF:LifecycleStatus: SpecIF:LifecycleStatusReleased
- SpecIF:LocalTerm: not to evaluate, not-to-evaluate

## ReqIF-WF.CustomerStatus.ToEvaluate (SpecIF:TermPropertyValue)
- dcterms:description: For the corresponding object an evaluation is expected by the supplier.
  - Attribute can be set to this value during the first transmission
  - Attribute can be changed to this value during the assessment process to indicate that a requirement has been modified and must be re-evaluated
- SpecIF:Domain: Automotive Stakeholder Request Clarification Process
- SpecIF:LifecycleStatus: SpecIF:LifecycleStatusReleased
- SpecIF:LocalTerm: to evaluate, to-evaluate

## ReqIF-WF.CustomerStatus.Accepted (SpecIF:TermPropertyValue)
- dcterms:description: The supplier evaluation is accepted by the customer.
- SpecIF:Domain: Automotive Stakeholder Request Clarification Process
- SpecIF:LifecycleStatus: SpecIF:LifecycleStatusReleased
- SpecIF:LocalTerm: accepted

## ReqIF-WF.CustomerStatus.NotAccepted (SpecIF:TermPropertyValue)
- dcterms:description: The supplier evaluation is not accepted by the customer.
  - Setting this status terminates the evaluation for this object. The conflict must be solved in the further project course outside of this workflow.
- SpecIF:Domain: Automotive Stakeholder Request Clarification Process
- SpecIF:LifecycleStatus: SpecIF:LifecycleStatusReleased
- SpecIF:LocalTerm: not accepted, not-accepted

## ReqIF-WF.CustomerStatus.ToBeClarified (SpecIF:TermPropertyValue)
- dcterms:description: The requirement has to be clarified with the supplier. Details in [[ReqIF-WF.CustomerComment]].
- SpecIF:Domain: Automotive Stakeholder Request Clarification Process
- SpecIF:LifecycleStatus: SpecIF:LifecycleStatusReleased
- SpecIF:LocalTerm: to be clarified, to-clarify

## ReqIF-WF.CustomerStatus.ProposedToDiscard (SpecIF:TermPropertyValue)
- dcterms:description: The requirement is marked as invalid and has to be discarded.

  NOTE: This value is OPTIONAL until the new ReqIF-WF process is well-established in industry.
- SpecIF:Domain: Automotive Stakeholder Request Clarification Process
- SpecIF:LifecycleStatus: SpecIF:LifecycleStatusReleased
- SpecIF:LocalTerm: proposed to discard

## ReqIF-WF.CustomerStatus.Discarded (SpecIF:TermPropertyValue)
- dcterms:description: The requirement has been marked explicitly as discarded by the customer.
- SpecIF:Domain: Automotive Stakeholder Request Clarification Process
- SpecIF:LifecycleStatus: SpecIF:LifecycleStatusReleased
- SpecIF:LocalTerm: discarded

## ReqIF-WF.SupplierStatus.Agreed (SpecIF:TermPropertyValue)
- dcterms:description: The supplier accepts the requirement.
- SpecIF:Domain: Automotive Stakeholder Request Clarification Process
- SpecIF:LifecycleStatus: SpecIF:LifecycleStatusReleased
- SpecIF:LocalTerm: agreed

## ReqIF-WF.SupplierStatus.NotAgreed (SpecIF:TermPropertyValue)
- dcterms:description: The supplier does not accept the requirement. Details must be declared in [[ReqIF-WF.SupplierComment]].
- SpecIF:Domain: Automotive Stakeholder Request Clarification Process
- SpecIF:LifecycleStatus: SpecIF:LifecycleStatusReleased
- SpecIF:LocalTerm: not agreed, not-agreed

## ReqIF-WF.SupplierStatus.AgreedWithComment (SpecIF:TermPropertyValue)
- dcterms:description: The supplier accepts the requirement with restrictions. The restrictions are explained by the supplier in the comment attribute [[ReqIF-WF.SupplierComment]].
- SpecIF:Domain: Automotive Stakeholder Request Clarification Process
- SpecIF:LifecycleStatus: SpecIF:LifecycleStatusReleased
- SpecIF:LocalTerm: agreed with comment, partly-agreed

## ReqIF-WF.SupplierStatus.ToBeClarified (SpecIF:TermPropertyValue)
- dcterms:description: The supplier requires clarification. The supplier must actively clarify the matter with the customer. Details must be declared in [[ReqIF-WF.SupplierComment]].
- SpecIF:Domain: Automotive Stakeholder Request Clarification Process
- SpecIF:LifecycleStatus: SpecIF:LifecycleStatusReleased
- SpecIF:LocalTerm: to be clarified, to-clarify

## ReqIF-WF.SupplierStatus.DiscardedDeployed (SpecIF:TermPropertyValue)
- dcterms:description: The supplier confirms that he will not implement the discarded requirement.
- SpecIF:Domain: Automotive Stakeholder Request Clarification Process
- SpecIF:LifecycleStatus: SpecIF:LifecycleStatusReleased
- SpecIF:LocalTerm: discarded

## Statements
- SpecIF:satisfies SpecIF:isSynonymOf oslc_rm:satisfies
- SpecIF:SubClass SpecIF:isSynonymOf dcterms:type
- oslc_rm:satisfiedBy SpecIF:isAntonymOf oslc_rm:satisfies
- oslc_rm:elaboratedBy SpecIF:isAntonymOf oslc_rm:elaborates
- oslc_rm:specifiedBy SpecIF:isAntonymOf oslc_rm:specifies
- oslc_rm:decomposedBy SpecIF:isAntonymOf oslc_rm:decomposes
- oslc_rm:constrainedBy SpecIF:isAntonymOf oslc_rm:constrains
- SpecIF:follows SpecIF:isAntonymOf SpecIF:precedes
- UML:isGeneralizationOf SpecIF:isAntonymOf UML:isSpecializationOf
- SpecIF:sameAs SpecIF:isSynonymOf owl:sameAs
- SpecIF:Id SpecIF:isSynonymOf dcterms:identifier
- SpecIF:createdBy SpecIF:isSynonymOf dcterms:creator
- SpecIF:createdAt SpecIF:isSynonymOf dcterms:created
- SpecIF:changedAt SpecIF:isSynonymOf dcterms:modified
- SpecIF:Creation SpecIF:isSynonymOf SpecIF:Instantiation
- SpecIF:Source SpecIF:isSynonymOf SpecIF:Subject
- SpecIF:Target SpecIF:isSynonymOf SpecIF:Object
- IREB:RequirementTypeFunction SpecIF:isSynonymOf IREB:FunctionalRequirement
- IREB:RequirementTypeQuality SpecIF:isSynonymOf IREB:QualityRequirement
- IREB:RequirementTypeConstraint SpecIF:isSynonymOf IREB:Constraint
- SpecIF:isInverseOf SpecIF:isSynonymOf SpecIF:isAntonymOf
- SpecIF:Stereotype SpecIF:isSynonymOf UML:Stereotype
- UML:Stereotype SpecIF:isSynonymOf dcterms:type
- SpecIF:SubClass SpecIF:isSynonymOf UML:Stereotype
- FMC:Actor SpecIF:isEligibleAsSubject SpecIF:reads
- FMC:State SpecIF:isEligibleAsObject SpecIF:reads
- FMC:Actor SpecIF:isEligibleAsSubject SpecIF:writes
- FMC:State SpecIF:isEligibleAsObject SpecIF:writes
- FMC:Actor SpecIF:isEligibleAsSubject SpecIF:stores
- FMC:State SpecIF:isEligibleAsObject SpecIF:stores
- SpecIF:signals UML:isSpecializationOf SpecIF:precedes
- SpecIF:triggers UML:isSpecializationOf SpecIF:precedes
- FMC:receivesFrom SpecIF:isAntonymOf FMC:sendsTo
- FMC:sendsTo UML:isSpecializationOf FMC:communicatesWith
- FMC:receivesFrom UML:isSpecializationOf FMC:communicatesWith
- FMC:Actor SpecIF:isEligibleAsSubject SpecIF:serves
- FMC:Actor SpecIF:isEligibleAsObject SpecIF:serves
- UML:isSpecialisationOf SpecIF:isSynonymOf UML:isSpecializationOf
- UML:isGeneralisationOf SpecIF:isSynonymOf UML:isGeneralizationOf
- HIS:OemStatus SpecIF:isSynonymOf ReqIF-WF.CustomerStatus
- HIS:SupplierComment SpecIF:isSynonymOf ReqIF-WF.SupplierComment
- HIS:SupplierStatus SpecIF:isSynonymOf ReqIF-WF.SupplierStatus
- HIS:OemComment SpecIF:isSynonymOf ReqIF-WF.CustomerComment
- UML:isGeneralisationOf SpecIF:isAntonymOf UML:isSpecialisationOf
- W3C:Vocabulary SpecIF:isSynonymOf W3C:Ontology
- SpecIF:Priority SpecIF:hasEnumValue SpecIF:priorityHigh
- SpecIF:Priority SpecIF:hasEnumValue SpecIF:priorityRatherHigh
- SpecIF:Priority SpecIF:hasEnumValue SpecIF:priorityMedium
- SpecIF:Priority SpecIF:hasEnumValue SpecIF:priorityRatherLow
- SpecIF:Priority SpecIF:hasEnumValue SpecIF:priorityLow
- SpecIF:LifecycleStatus SpecIF:hasEnumValue SpecIF:LifecycleStatusInitial
- SpecIF:LifecycleStatus SpecIF:hasEnumValue SpecIF:LifecycleStatusDrafted
- SpecIF:LifecycleStatus SpecIF:hasEnumValue SpecIF:LifecycleStatusSubmitted
- SpecIF:LifecycleStatus SpecIF:hasEnumValue SpecIF:LifecycleStatusApproved
- SpecIF:LifecycleStatus SpecIF:hasEnumValue SpecIF:LifecycleStatusReady
- SpecIF:LifecycleStatus SpecIF:hasEnumValue SpecIF:LifecycleStatusDone
- SpecIF:LifecycleStatus SpecIF:hasEnumValue SpecIF:LifecycleStatusValidated
- SpecIF:LifecycleStatus SpecIF:hasEnumValue SpecIF:LifecycleStatusReleased
- SpecIF:LifecycleStatus SpecIF:hasEnumValue SpecIF:LifecycleStatusDeprecated
- SpecIF:LifecycleStatus SpecIF:hasEnumValue SpecIF:LifecycleStatusWithdrawn
- SpecIF:LifecycleStatus SpecIF:hasEnumValue SpecIF:LifecycleStatusPostponed
- SpecIF:LifecycleStatus SpecIF:hasEnumValue SpecIF:LifecycleStatusRejected
- IREB:Requirement SpecIF:isEligibleAsSubject IREB:refines
- IREB:Requirement SpecIF:isEligibleAsObject IREB:refines
- SpecIF:Paragraph SpecIF:hasProperty dcterms:title
- SpecIF:Paragraph SpecIF:hasProperty dcterms:description
- SpecIF:commentRefersTo UML:isSpecializationOf SpecIF:refersTo
- SpecIF:Comment SpecIF:isEligibleAsSubject SpecIF:commentRefersTo
- FMC:Actor SpecIF:isEligibleAsObject SpecIF:commentRefersTo
- FMC:State SpecIF:isEligibleAsObject SpecIF:commentRefersTo
- FMC:Event SpecIF:isEligibleAsObject SpecIF:commentRefersTo
- SpecIF:Hierarchy SpecIF:hasProperty dcterms:title
- SpecIF:Hierarchy SpecIF:hasProperty dcterms:description
- SpecIF:Hierarchy SpecIF:hasProperty dcterms:type
- SpecIF:Paragraph SpecIF:hasProperty dcterms:type
- SpecIF:View UML:isSpecializationOf SpecIF:Paragraph
- FMC:Plan SpecIF:isSynonymOf SpecIF:View
- SpecIF:Diagram SpecIF:isSynonymOf SpecIF:View
- SpecIF:View SpecIF:hasProperty SpecIF:Notation
- SpecIF:Heading UML:isSpecializationOf SpecIF:Paragraph
- SpecIF:Paragraph SpecIF:isEligibleAsObject SpecIF:commentRefersTo
- SpecIF:Heading SpecIF:isEligibleAsObject SpecIF:commentRefersTo
- SpecIF:View SpecIF:isEligibleAsObject SpecIF:commentRefersTo
- SpecIF:ModelElement SpecIF:hasProperty dcterms:title
- SpecIF:ModelElement SpecIF:hasProperty dcterms:description
- SpecIF:ModelElement SpecIF:hasProperty dcterms:type
- FMC:Actor UML:isSpecializationOf SpecIF:ModelElement
- FMC:State UML:isSpecializationOf SpecIF:ModelElement
- FMC:Event UML:isSpecializationOf SpecIF:ModelElement
- SpecIF:Collection UML:isSpecializationOf SpecIF:ModelElement
- SpecIF:View SpecIF:isEligibleAsSubject SpecIF:shows
- FMC:Actor SpecIF:isEligibleAsObject SpecIF:shows
- FMC:State SpecIF:isEligibleAsObject SpecIF:shows
- FMC:Event SpecIF:isEligibleAsObject SpecIF:shows
- SpecIF:Collection SpecIF:isEligibleAsObject SpecIF:shows
- SpecIF:Collection SpecIF:isEligibleAsObject SpecIF:commentRefersTo
- SpecIF:Comment SpecIF:hasProperty dcterms:description
- IREB:Requirement UML:isSpecializationOf SpecIF:Paragraph
- IREB:Requirement SpecIF:hasProperty SpecIF:Priority
- SpecIF:Feature UML:isSpecializationOf SpecIF:Paragraph
- SpecIF:Feature SpecIF:hasProperty SpecIF:Priority
- ReqIF-WF.Requirement UML:isSpecializationOf IREB:Requirement
- ReqIF-WF.Requirement SpecIF:hasProperty ReqIF-WF.SupplierStatus
- ReqIF-WF.Requirement SpecIF:hasProperty ReqIF-WF.SupplierComment
- ReqIF-WF.Requirement SpecIF:hasProperty ReqIF-WF.CustomerStatus
- ReqIF-WF.Requirement SpecIF:hasProperty ReqIF-WF.CustomerComment
- ReqIF-WF.SupplierStatus SpecIF:hasEnumValue ReqIF-WF.SupplierStatus.ToBeClarified
- ReqIF-WF.SupplierStatus SpecIF:hasEnumValue ReqIF-WF.SupplierStatus.AgreedWithComment
- ReqIF-WF.SupplierStatus SpecIF:hasEnumValue ReqIF-WF.SupplierStatus.Agreed
- ReqIF-WF.SupplierStatus SpecIF:hasEnumValue ReqIF-WF.SupplierStatus.NotAgreed
- ReqIF-WF.SupplierStatus SpecIF:hasEnumValue ReqIF-WF.SupplierStatus.DiscardedDeployed
- ReqIF-WF.CustomerStatus SpecIF:hasEnumValue ReqIF-WF.CustomerStatus.ToEvaluate
- ReqIF-WF.CustomerStatus SpecIF:hasEnumValue ReqIF-WF.CustomerStatus.ToBeClarified
- ReqIF-WF.CustomerStatus SpecIF:hasEnumValue ReqIF-WF.CustomerStatus.NotAccepted
- ReqIF-WF.CustomerStatus SpecIF:hasEnumValue ReqIF-WF.CustomerStatus.Accepted
- ReqIF-WF.CustomerStatus SpecIF:hasEnumValue ReqIF-WF.CustomerStatus.NotToEvaluate
- ReqIF-WF.CustomerStatus SpecIF:hasEnumValue ReqIF-WF.CustomerStatus.ProposedToDiscard
- ReqIF-WF.CustomerStatus SpecIF:hasEnumValue ReqIF-WF.CustomerStatus.Discarded
- SpecIF:EngineeringDiscipline SpecIF:hasEnumValue SpecIF:EngineeringDisciplineMechanics
- SpecIF:EngineeringDiscipline SpecIF:hasEnumValue SpecIF:EngineeringDisciplineElectronics
- SpecIF:EngineeringDiscipline SpecIF:hasEnumValue SpecIF:EngineeringDisciplineSoftware
- SpecIF:EngineeringDiscipline SpecIF:hasEnumValue SpecIF:EngineeringDisciplineSafety
- SpecIF:EngineeringDiscipline SpecIF:hasEnumValue SpecIF:EngineeringDisciplineSystem
- SpecIF:TermResourceClass UML:isSpecializationOf SpecIF:OntologyTerm
- SpecIF:TermStatementClass UML:isSpecializationOf SpecIF:OntologyTerm
- SpecIF:TermPropertyClass UML:isSpecializationOf SpecIF:OntologyTerm
- SpecIF:TermPropertyValue UML:isSpecializationOf SpecIF:OntologyTerm
- bpmn:group SpecIF:isSynonymOf SpecIF:Collection
- oslc_rm:elaborates SpecIF:isSynonymOf IREB:refines
- IREB:Requirement SpecIF:hasProperty IREB:RequirementType
- ReqIF-WF.Requirement SpecIF:isEligibleAsSubject IREB:refines
- ReqIF-WF.Requirement SpecIF:isEligibleAsObject IREB:refines
- IREB:Requirement SpecIF:isEligibleAsSubject SpecIF:duplicates
- ReqIF-WF.Requirement SpecIF:isEligibleAsSubject SpecIF:duplicates
- IREB:Requirement SpecIF:isEligibleAsObject SpecIF:duplicates
- ReqIF-WF.Requirement SpecIF:isEligibleAsObject SpecIF:duplicates
- IREB:Requirement SpecIF:isEligibleAsSubject SpecIF:contradicts
- ReqIF-WF.Requirement SpecIF:isEligibleAsSubject SpecIF:contradicts
- IREB:Requirement SpecIF:isEligibleAsObject SpecIF:contradicts
- ReqIF-WF.Requirement SpecIF:isEligibleAsObject SpecIF:contradicts
- SpecIF:Perspective SpecIF:isSynonymOf SpecIF:StakeholderGroup
- IREB:Requirement SpecIF:hasProperty SpecIF:StakeholderGroup
- SpecIF:StakeholderGroup SpecIF:hasEnumValue SpecIF:StakeholderGroupRegulation
- SpecIF:StakeholderGroup SpecIF:hasEnumValue SpecIF:StakeholderGroupBusiness
- SpecIF:StakeholderGroup SpecIF:hasEnumValue SpecIF:StakeholderGroupUser
- SpecIF:StakeholderGroup SpecIF:hasEnumValue SpecIF:StakeholderGroupOperation
- SpecIF:Feature SpecIF:isSynonymOf IREB:Requirement
- IREB:RequirementType SpecIF:hasEnumValue SpecIF:Feature
- IREB:RequirementType SpecIF:hasEnumValue SpecIF:UserStory
- IREB:RequirementType SpecIF:hasEnumValue IREB:FunctionalRequirement
- IREB:RequirementType SpecIF:hasEnumValue IREB:QualityRequirement
- IREB:RequirementType SpecIF:hasEnumValue IREB:Constraint
- SpecIF:stores SpecIF:isSynonymOf SpecIF:accesses
- SpecIF:reads UML:isSpecializationOf SpecIF:accesses
- SpecIF:writes UML:isSpecializationOf SpecIF:accesses
- FMC:modifies SpecIF:isSynonymOf SpecIF:accesses
- FMC:Actor SpecIF:isEligibleAsSubject SpecIF:follows
- FMC:Actor SpecIF:isEligibleAsObject SpecIF:follows
- FMC:Actor SpecIF:isEligibleAsSubject SpecIF:precedes
- FMC:Actor SpecIF:isEligibleAsObject SpecIF:precedes
- FMC:Actor SpecIF:isEligibleAsSubject FMC:communicatesWith
- FMC:Actor SpecIF:isEligibleAsObject FMC:communicatesWith
- FMC:Actor SpecIF:isEligibleAsSubject FMC:sendsTo
- FMC:Actor SpecIF:isEligibleAsObject FMC:sendsTo
- FMC:Actor SpecIF:isEligibleAsSubject FMC:receivesFrom
- FMC:Actor SpecIF:isEligibleAsObject FMC:receivesFrom
- FMC:Actor SpecIF:isEligibleAsSubject SpecIF:accesses
- FMC:State SpecIF:isEligibleAsObject SpecIF:accesses
- IREB:Requirement SpecIF:isEligibleAsSubject SpecIF:dependsOn
- ReqIF-WF.Requirement SpecIF:isEligibleAsSubject SpecIF:dependsOn
- IREB:Requirement SpecIF:isEligibleAsObject SpecIF:dependsOn
- ReqIF-WF.Requirement SpecIF:isEligibleAsObject SpecIF:dependsOn
- IREB:Requirement SpecIF:isEligibleAsSubject SysML:traces
- ReqIF-WF.Requirement SpecIF:isEligibleAsSubject SysML:traces
- IREB:Requirement SpecIF:isEligibleAsObject SysML:traces
- ReqIF-WF.Requirement SpecIF:isEligibleAsObject SysML:traces
- IREB:Requirement SpecIF:isEligibleAsSubject SysML:isDerivedFrom
- ReqIF-WF.Requirement SpecIF:isEligibleAsSubject SysML:isDerivedFrom
- IREB:Requirement SpecIF:isEligibleAsObject SysML:isDerivedFrom
- ReqIF-WF.Requirement SpecIF:isEligibleAsObject SysML:isDerivedFrom
- FMC:Actor SpecIF:isEligibleAsSubject UML:isComposedOf
- FMC:Actor SpecIF:isEligibleAsObject UML:isComposedOf
- FMC:Actor SpecIF:isEligibleAsSubject UML:isAggregatedBy
- FMC:Actor SpecIF:isEligibleAsObject UML:isAggregatedBy
- FMC:Actor SpecIF:isEligibleAsSubject UML:extends
- FMC:Actor SpecIF:isEligibleAsObject UML:extends
- FMC:Actor SpecIF:isEligibleAsSubject SysML:includes
- FMC:Actor SpecIF:isEligibleAsObject SysML:includes
- FMC:Actor SpecIF:isEligibleAsSubject SysML:isAllocatedTo
- FMC:Actor SpecIF:isEligibleAsObject SysML:isAllocatedTo
- FMC:State SpecIF:isEligibleAsSubject UML:isAssociatedWith
- FMC:State SpecIF:isEligibleAsObject UML:isAssociatedWith
- FMC:Actor SpecIF:isEligibleAsSubject SpecIF:contains
- FMC:State SpecIF:isEligibleAsSubject SpecIF:contains
- FMC:Actor SpecIF:isEligibleAsObject SpecIF:contains
- FMC:State SpecIF:isEligibleAsObject SpecIF:contains
- FMC:Event SpecIF:isEligibleAsObject SpecIF:contains
- SpecIF:Collection SpecIF:isEligibleAsSubject SpecIF:contains
- FMC:Actor SpecIF:isEligibleAsSubject FMC:contains
- FMC:State SpecIF:isEligibleAsSubject FMC:contains
- FMC:Actor SpecIF:isEligibleAsObject FMC:contains
- FMC:State SpecIF:isEligibleAsObject FMC:contains
- FMC:Event SpecIF:isEligibleAsObject FMC:contains
- SpecIF:Collection SpecIF:isEligibleAsObject SpecIF:contains
- FMC:Actor SpecIF:isEligibleAsSubject UML:composes
- FMC:Actor SpecIF:isEligibleAsObject UML:composes
- UML:isComposedOf SpecIF:isAntonymOf UML:composes
- UML:isAggregatedBy SpecIF:isAntonymOf UML:aggregates
- FMC:Actor SpecIF:isEligibleAsSubject UML:aggregates
- FMC:Actor SpecIF:isEligibleAsObject UML:aggregates
- oslc_rm:decomposes SpecIF:isSynonymOf UML:isComposedOf
- oslc_rm:decomposedBy SpecIF:isSynonymOf UML:composes
- SpecIF:contains SpecIF:hasProperty dcterms:type
- FMC:Plan UML:isSpecializationOf SpecIF:Paragraph
- FMC:Plan SpecIF:isEligibleAsObject SpecIF:commentRefersTo
- FMC:Plan SpecIF:isEligibleAsSubject SpecIF:shows
- ReqIF.Text SpecIF:isSynonymOf dcterms:description
- ReqIF.Name SpecIF:isSynonymOf dcterms:title
- ReqIF.ForeignID SpecIF:isSynonymOf dcterms:identifier
- ReqIF.ForeignState SpecIF:isSynonymOf SpecIF:LifecycleStatus
- ReqIF.Category SpecIF:isSynonymOf dcterms:type
- ArchiMate:Viewpoint UML:isSpecializationOf SpecIF:Paragraph
- ArchiMate:Viewpoint SpecIF:hasProperty SpecIF:Notation
- ArchiMate:Viewpoint SpecIF:isEligibleAsObject SpecIF:commentRefersTo
- ArchiMate:Viewpoint SpecIF:isEligibleAsSubject SpecIF:shows
- ArchiMate:Viewpoint SpecIF:isSynonymOf SpecIF:View
- FMC:Plan SpecIF:hasProperty SpecIF:Notation
- SpecIF:Outline SpecIF:hasProperty SpecIF:LifecycleStatus
- SpecIF:Hierarchy SpecIF:hasProperty SpecIF:LifecycleStatus
- SpecIF:Outline UML:isSpecializationOf SpecIF:Paragraph
- SpecIF:BillOfMaterials UML:isSpecializationOf SpecIF:Outline
- SpecIF:BusinessProcess UML:isSpecializationOf SpecIF:View
- SpecIF: SpecIF:isNamespace SpecIF:Paragraph
- SpecIF: SpecIF:isNamespace SpecIF:Heading
- SpecIF: SpecIF:isNamespace SpecIF:View
- ArchiMate: SpecIF:isNamespace ArchiMate:Viewpoint
- SpecIF: SpecIF:isNamespace SpecIF:Diagram
- SpecIF: SpecIF:isNamespace SpecIF:Feature
- IREB: SpecIF:isNamespace IREB:Requirement
- ReqIF-WF. SpecIF:isNamespace ReqIF-WF.Requirement
- SpecIF: SpecIF:isNamespace SpecIF:ModelElement
- FMC: SpecIF:isNamespace FMC:Plan
- FMC: SpecIF:isNamespace FMC:Actor
- FMC: SpecIF:isNamespace FMC:State
- FMC: SpecIF:isNamespace FMC:Event
- SpecIF: SpecIF:isNamespace SpecIF:Collection
- ReqIF-WF. SpecIF:isNamespace ReqIF-WF.CustomerComment
- ReqIF-WF. SpecIF:isNamespace ReqIF-WF.CustomerStatus
- ReqIF-WF. SpecIF:isNamespace ReqIF-WF.SupplierComment
- ReqIF-WF. SpecIF:isNamespace ReqIF-WF.SupplierStatus
- ReqIF. SpecIF:isNamespace ReqIF.Category
- ReqIF. SpecIF:isNamespace ReqIF.ForeignID
- ReqIF. SpecIF:isNamespace ReqIF.ForeignState
- ReqIF. SpecIF:isNamespace ReqIF.Name
- ReqIF. SpecIF:isNamespace ReqIF.Text
- FMC: SpecIF:isNamespace FMC:contains
- FMC: SpecIF:isNamespace FMC:modifies
- IREB: SpecIF:isNamespace IREB:Constraint
- IREB: SpecIF:isNamespace IREB:Stakeholder
- IREB: SpecIF:isNamespace IREB:Risk
- IREB: SpecIF:isNamespace IREB:FunctionalRequirement
- IREB: SpecIF:isNamespace IREB:QualityRequirement
- IREB: SpecIF:isNamespace IREB:RequirementType
- IREB: SpecIF:isNamespace IREB:RequirementTypeConstraint
- IREB: SpecIF:isNamespace IREB:RequirementTypeFunction
- IREB: SpecIF:isNamespace IREB:RequirementTypeQuality
- IREB: SpecIF:isNamespace IREB:refines
- bpmn: SpecIF:isNamespace bpmn:group
- bpmn: SpecIF:isNamespace bpmn:processStep
- bpmn: SpecIF:isNamespace bpmn:timer
- bpmn: SpecIF:isNamespace bpmn:startEvent
- bpmn: SpecIF:isNamespace bpmn:intermediateEvent
- bpmn: SpecIF:isNamespace bpmn:endEvent
- bpmn: SpecIF:isNamespace bpmn:join
- ArchiMate: SpecIF:isNamespace ArchiMate:unites
- foaf: SpecIF:isNamespace foaf:Person
- SpecIF: SpecIF:isNamespace SpecIF:Glossary
- SpecIF: SpecIF:isNamespace SpecIF:Hierarchy
- SpecIF: SpecIF:isNamespace SpecIF:Diagram
- SpecIF: SpecIF:isNamespace SpecIF:Damage
- SpecIF: SpecIF:isNamespace SpecIF:Benefit
- SpecIF: SpecIF:isNamespace SpecIF:BillOfMaterials
- SpecIF: SpecIF:isNamespace SpecIF:BusinessProcess
- SpecIF: SpecIF:isNamespace SpecIF:Category
- SpecIF: SpecIF:isNamespace SpecIF:Comment
- SpecIF: SpecIF:isNamespace SpecIF:DueDate
- SpecIF: SpecIF:isNamespace SpecIF:FitCriteria
- SpecIF: SpecIF:isNamespace SpecIF:LifecycleStatus
- SpecIF:Category SpecIF:isSynonymOf dcterms:type
- SpecIF: SpecIF:isNamespace SpecIF:Revision
- ReqIF. SpecIF:isNamespace ReqIF.Revision
- ReqIF.Revision SpecIF:isSynonymOf SpecIF:Revision
- ReqIF. SpecIF:isNamespace ReqIF.ForeignCreatedBy
- ReqIF.ForeignCreatedBy SpecIF:isSynonymOf dcterms:creator
- ReqIF. SpecIF:isNamespace ReqIF.ChapterName
- W3C: SpecIF:isNamespace W3C:Ontology
- W3C: SpecIF:isNamespace W3C:Vocabulary
- owl: SpecIF:isNamespace owl:sameAs
- dcterms: SpecIF:isNamespace dcterms:title
- dcterms: SpecIF:isNamespace dcterms:description
- dcterms: SpecIF:isNamespace dcterms:type
- dcterms: SpecIF:isNamespace dcterms:identifier
- dcterms: SpecIF:isNamespace dcterms:creator
- dcterms: SpecIF:isNamespace dcterms:created
- dcterms: SpecIF:isNamespace dcterms:modified
- dcterms: SpecIF:isNamespace dcterms:contributor
- dcterms: SpecIF:isNamespace dcterms:rightsHolder
- dcterms: SpecIF:isNamespace dcterms:rights
- dcterms: SpecIF:isNamespace dcterms:subject
- rdf: SpecIF:isNamespace rdf:type
- foaf:Person SpecIF:isSynonymOf schema:Person
- schema: SpecIF:isNamespace schema:Person
- schema: SpecIF:isNamespace schema:Organization
- schema: SpecIF:isNamespace schema:Role
- ReqIF. SpecIF:isNamespace ReqIF.ChapterNumber
- ReqIF. SpecIF:isNamespace ReqIF.Prefix
- ReqIF. SpecIF:isNamespace ReqIF.Description
- ReqIF. SpecIF:isNamespace ReqIF.FitCriteria
- ReqIF. SpecIF:isNamespace ReqIF.ChangeDescription
- ReqIF. SpecIF:isNamespace ReqIF.Project
- ReqIF. SpecIF:isNamespace ReqIF.AssociatedFiles
- ReqIF.Description SpecIF:isSynonymOf dcterms:description
- ReqIF.FitCriteria SpecIF:isSynonymOf SpecIF:FitCriteria
- dcterms: SpecIF:isNamespace oslc:serviceProvider
- oslc_rm: SpecIF:isNamespace oslc_rm:implementedBy
- oslc_rm:implementedBy SpecIF:isAntonymOf oslc_rm:implements
- oslc_rm: SpecIF:isNamespace oslc_rm:implements
- SpecIF:implements SpecIF:isSynonymOf oslc_rm:implements
- oslc_rm:validatedBy SpecIF:isAntonymOf oslc_rm:validates
- oslc_rm: SpecIF:isNamespace oslc_rm:validatedBy
- oslc_rm: SpecIF:isNamespace oslc_rm:validates
- oslc_rm: SpecIF:isNamespace oslc_rm:decomposes
- oslc_rm: SpecIF:isNamespace oslc_rm:decomposedBy
- ArchiMate:isComposedOf SpecIF:isSynonymOf UML:isComposedOf
- ArchiMate:isComposedOf SpecIF:isSynonymOf oslc_rm:decomposedBy
- ArchiMate:composes SpecIF:isSynonymOf UML:composes
- ArchiMate:composes SpecIF:isAntonymOf ArchiMate:isComposedOf
- ArchiMate:aggregates SpecIF:isSynonymOf UML:aggregates
- ArchiMate:aggregates UML:isSpecializationOf ArchiMate:unites
- ArchiMate:isComposedOf UML:isSpecializationOf ArchiMate:unites
- ArchiMate:aggregates SpecIF:isSynonymOf UML:isAggregatedBy
- SpecIF:Requirement SpecIF:isSynonymOf IREB:Requirement
- SpecIF: SpecIF:isNamespace SpecIF:Requirement
- SpecIF:Hierarchy SpecIF:isSynonymOf SpecIF:Outline
- SpecIF:Perspective SpecIF:hasEnumValue SpecIF:PerspectiveBusiness
- SpecIF:Perspective SpecIF:hasEnumValue SpecIF:PerspectiveStakeholder
- SpecIF:Perspective SpecIF:hasEnumValue SpecIF:PerspectiveUser
- SpecIF:Perspective SpecIF:hasEnumValue SpecIF:PerspectiveOperator
- SpecIF:Perspective SpecIF:hasEnumValue SpecIF:PerspectiveSystem
- SpecIF:PerspectiveBusiness SpecIF:isSynonymOf SpecIF:StakeholderGroupBusiness
- SpecIF:PerspectiveUser SpecIF:isSynonymOf SpecIF:StakeholderGroupUser
- SpecIF:PerspectiveOperator SpecIF:isSynonymOf SpecIF:StakeholderGroupOperation
- IREB:Risk SpecIF:hasProperty SpecIF:Probability
- IREB:Risk SpecIF:hasProperty SpecIF:Impact
- FMC:contains SpecIF:isSynonymOf SpecIF:contains
- ArchiMate:unites SpecIF:isSynonymOf SpecIF:contains
- IREB:Requirement SpecIF:isEligibleAsObject oslc_rm:satisfies
- ReqIF-WF.Requirement SpecIF:isEligibleAsObject oslc_rm:satisfies
- FMC:Actor SpecIF:isEligibleAsSubject oslc_rm:satisfies
- FMC:State SpecIF:isEligibleAsSubject oslc_rm:satisfies
- FMC:Event SpecIF:isEligibleAsSubject oslc_rm:satisfies
- SpecIF:Collection SpecIF:isEligibleAsSubject oslc_rm:satisfies
- IREB:Requirement SpecIF:isEligibleAsSubject oslc_rm:satisfiedBy
- ReqIF-WF.Requirement SpecIF:isEligibleAsSubject oslc_rm:satisfiedBy
- FMC:Actor SpecIF:isEligibleAsObject oslc_rm:satisfiedBy
- FMC:State SpecIF:isEligibleAsObject oslc_rm:satisfiedBy
- FMC:Event SpecIF:isEligibleAsObject oslc_rm:satisfiedBy
- SpecIF:Collection SpecIF:isEligibleAsObject oslc_rm:satisfiedBy
- ArchiMate:accesses SpecIF:isSynonymOf SpecIF:accesses
- ArchiMate: SpecIF:isNamespace ArchiMate:realizes
- ArchiMate:isRealizedBy SpecIF:isAntonymOf ArchiMate:realizes
- SysML:isAllocatedTo SpecIF:isSynonymOf ArchiMate:isRealizedBy
- ArchiMate:realizes UML:isSpecializationOf ArchiMate:unites
- FMC:Actor SpecIF:isEligibleAsSubject ArchiMate:serves
- FMC:Actor SpecIF:isEligibleAsObject ArchiMate:serves
- SpecIF:serves SpecIF:isSynonymOf ArchiMate:serves
- ArchiMate: SpecIF:isNamespace ArchiMate:serves
- ArchiMate: SpecIF:isNamespace ArchiMate:isAssignedTo
- ArchiMate:isAssignedTo UML:isSpecializationOf ArchiMate:unites
- SysML:isAllocatedTo SpecIF:isSynonymOf ArchiMate:isAssignedTo
- UML: SpecIF:isNamespace UML:isAssociatedWith
- UML: SpecIF:isNamespace UML:isComposedOf
- SysML:isComposedOf SpecIF:isSynonymOf UML:isComposedOf
- SysML:isComposedOf SpecIF:isAntonymOf UML:composes
- UML: SpecIF:isNamespace UML:aggregates
- UML:isAggregatedBy SpecIF:isAntonymOf SysML:aggregates
- SysML:aggregates SpecIF:isSynonymOf UML:aggregates
- SysML: SpecIF:isNamespace SysML:isUsedBy
- SysML:isUsedBy SpecIF:isAntonymOf SysML:uses
- SpecIF:issueRefersTo UML:isSpecializationOf SpecIF:refersTo
- SpecIF: SpecIF:isNamespace SpecIF:Size
- SpecIF:Size SpecIF:hasEnumValue SpecIF:sizeXL
- SpecIF:Size SpecIF:hasEnumValue SpecIF:sizeL
- SpecIF:Size SpecIF:hasEnumValue SpecIF:sizeM
- SpecIF:Size SpecIF:hasEnumValue SpecIF:sizeS
- SpecIF:Size SpecIF:hasEnumValue SpecIF:sizeXS
- SpecIF:DisciplineSystem SpecIF:isSynonymOf SpecIF:EngineeringDisciplineSystem
- SpecIF:DisciplineSystemEngineering SpecIF:isSynonymOf SpecIF:EngineeringDisciplineSystem
- SpecIF:DisciplineMechanics SpecIF:isSynonymOf SpecIF:EngineeringDisciplineMechanics
- SpecIF:DisciplineElectronics SpecIF:isSynonymOf SpecIF:EngineeringDisciplineElectronics
- SpecIF:DisciplineSoftware SpecIF:isSynonymOf SpecIF:EngineeringDisciplineSoftware
- SpecIF:DisciplineSafety SpecIF:isSynonymOf SpecIF:EngineeringDisciplineSafety
- SpecIF: SpecIF:isNamespace SpecIF:Folder
- SpecIF:Folder SpecIF:isSynonymOf SpecIF:Heading
- IREB: SpecIF:isNamespace IREB:refinedBy
- IREB:refinedBy SpecIF:isAntonymOf IREB:refines
- SpecIF: SpecIF:isNamespace SpecIF:Information
- SpecIF:Information SpecIF:isSynonymOf SpecIF:Paragraph
- UML: SpecIF:isNamespace UML:isSpecializationOf
- UML: SpecIF:isNamespace UML:isGeneralizationOf
- SpecIF: SpecIF:isNamespace SpecIF:isSpecializationOf
- SpecIF:isSpecializationOf SpecIF:isSynonymOf UML:isSpecializationOf
- SpecIF: SpecIF:isNamespace SpecIF:isGeneralizationOf
- SpecIF:isGeneralizationOf SpecIF:isSynonymOf UML:isGeneralizationOf
- IR: SpecIF:isNamespace IR:refersTo
- IR:refersTo SpecIF:isSynonymOf SpecIF:refersTo
- IR:Annotation SpecIF:isEligibleAsObject IR:approves
- IR:Annotation SpecIF:isEligibleAsObject IR:opposes
- IR: SpecIF:isNamespace IR:inheritsFrom
- IR: SpecIF:isNamespace IR:approves
- IR: SpecIF:isNamespace IR:opposes
- SpecIF: SpecIF:isNamespace SpecIF:realizes
- ArchiMate:realizes SpecIF:isSynonymOf SpecIF:realizes
- IR:inheritsFrom SpecIF:isSynonymOf UML:isSpecializationOf
- SpecIF: SpecIF:isNamespace SpecIF:inheritsFrom
- SpecIF:inheritsFrom SpecIF:isSynonymOf UML:isSpecializationOf
- SpecIF: SpecIF:isNamespace SpecIF:Id
- SpecIF: SpecIF:isNamespace SpecIF:Type
- SpecIF: SpecIF:isNamespace SpecIF:Stereotype
- SpecIF:Type SpecIF:isSynonymOf dcterms:type
- SpecIF: SpecIF:isNamespace SpecIF:LifecycleStatusReleased
- SpecIF: SpecIF:isNamespace SpecIF:Instantiation
- ReqIF-WF. SpecIF:isNamespace ReqIF-WF.Customer
- ReqIF-WF. SpecIF:isNamespace ReqIF-WF.Supplier
- SpecIF: SpecIF:isNamespace SpecIF:TermStatus
- SpecIF:TermStatus SpecIF:hasEnumValue SpecIF:LifecycleStatusExperimental
- SpecIF:TermStatus SpecIF:hasEnumValue SpecIF:LifecycleStatusSubmitted
- SpecIF:TermStatus SpecIF:hasEnumValue SpecIF:LifecycleStatusApproved
- SpecIF:TermStatus SpecIF:hasEnumValue SpecIF:LifecycleStatusEquivalent
- SpecIF:TermStatus SpecIF:hasEnumValue SpecIF:LifecycleStatusDeprecated
- SpecIF: SpecIF:isNamespace SpecIF:OntologyTerm
- SpecIF:OntologyTerm SpecIF:hasProperty dcterms:identifier
- SpecIF:OntologyTerm SpecIF:hasProperty SpecIF:Revision
- SpecIF:OntologyTerm SpecIF:hasProperty SpecIF:Term
- SpecIF:OntologyTerm SpecIF:hasProperty dcterms:description
- SpecIF:OntologyTerm SpecIF:hasProperty SpecIF:Domain
- SpecIF:OntologyTerm SpecIF:hasProperty SpecIF:TermStatus
- SpecIF:OntologyTerm SpecIF:hasProperty SpecIF:LocalTerm
- SpecIF: SpecIF:isNamespace SpecIF:TermPropertyClassURI
- SpecIF:TermPropertyClassURI UML:isSpecializationOf SpecIF:TermPropertyClass
- SpecIF:TermPropertyClassDuration UML:isSpecializationOf SpecIF:TermPropertyClass
- SpecIF:TermPropertyClassTimestamp UML:isSpecializationOf SpecIF:TermPropertyClass
- SpecIF:TermPropertyClassReal UML:isSpecializationOf SpecIF:TermPropertyClass
- SpecIF:TermPropertyClassInteger UML:isSpecializationOf SpecIF:TermPropertyClass
- SpecIF:TermPropertyClassBoolean UML:isSpecializationOf SpecIF:TermPropertyClass
- SpecIF:TermPropertyClassString UML:isSpecializationOf SpecIF:TermPropertyClass
- SpecIF: SpecIF:isNamespace SpecIF:TermPropertyClassString
- SpecIF: SpecIF:isNamespace SpecIF:TermPropertyClassBoolean
- SpecIF: SpecIF:isNamespace SpecIF:TermPropertyClassInteger
- SpecIF: SpecIF:isNamespace SpecIF:TermPropertyClassReal
- SpecIF: SpecIF:isNamespace SpecIF:TermPropertyClassTimestamp
- SpecIF: SpecIF:isNamespace SpecIF:Namespace
- ReqIF.ChapterName SpecIF:isSynonymOf dcterms:title
- IREB:RequirementType SpecIF:hasEnumValue SpecIF:PainPoint
- SpecIF: SpecIF:isNamespace SpecIF:isPluralOf
- SpecIF: SpecIF:isNamespace SpecIF:relates
- SpecIF: SpecIF:isNamespace SpecIF:Resource
- SpecIF: SpecIF:isNamespace SpecIF:Statement
- SpecIF:contains UML:isSpecializationOf SpecIF:relates
- SpecIF:accesses UML:isSpecializationOf SpecIF:relates
- SpecIF:writes UML:isSpecializationOf SpecIF:relates
- SpecIF:reads UML:isSpecializationOf SpecIF:relates
- SpecIF: SpecIF:isNamespace SpecIF:hasEnumValue
- SpecIF:TermPropertyClassString SpecIF:isEligibleAsSubject SpecIF:hasEnumValue
- SpecIF:TermResourceClass SpecIF:isEligibleAsObject SpecIF:hasEnumValue
- SpecIF:TermStatementClass SpecIF:isEligibleAsObject SpecIF:hasEnumValue
- SpecIF:TermPropertyValue SpecIF:isEligibleAsObject SpecIF:hasEnumValue
- SpecIF:Discipline SpecIF:isSynonymOf SpecIF:EngineeringDiscipline
- SpecIF:Status SpecIF:isSynonymOf SpecIF:LifecycleStatus
- SysML: SpecIF:isNamespace SpecIF:Reader
- SpecIF: SpecIF:isNamespace SpecIF:Editor
- SysML: SpecIF:isNamespace SysML:isSpecializationOf
- SysML:isSpecializationOf SpecIF:isSynonymOf UML:isSpecializationOf
- SysML: SpecIF:isNamespace SysML:isGeneralizationOf
- SysML:isGeneralizationOf SpecIF:isSynonymOf UML:isGeneralizationOf
- SysML:isAssociatedWith SpecIF:isSynonymOf UML:isAssociatedWith
- SpecIF:isAssociatedWith SpecIF:isSynonymOf UML:isAssociatedWith
- ReqIF. SpecIF:isNamespace ReqIF.ForeignModifiedOn
- ReqIF.ForeignModifiedOn SpecIF:isSynonymOf dcterms:modified
- ReqIF. SpecIF:isNamespace ReqIF.ForeignModifiedBy
- ReqIF.ForeignModifiedBy SpecIF:isSynonymOf SpecIF:changedBy
- ReqIF. SpecIF:isNamespace ReqIF.ForeignCreatedOn
- ReqIF.ForeignCreatedOn SpecIF:isSynonymOf dcterms:created
- bpmn: SpecIF:isNamespace bpmn:Pool
- bpmn:Pool UML:isSpecializationOf bpmn:Participant
- bpmn: SpecIF:isNamespace bpmn:Lane
- bpmn:Lane UML:isSpecializationOf bpmn:Participant
- bpmn:Participant UML:isSpecializationOf FMC:Actor
- bpmn:Lane SpecIF:isSynonymOf UML:Actor
- UML: SpecIF:isNamespace UML:Actor
- UML:Actor UML:isSpecializationOf FMC:Actor
- SpecIF:BusinessProcess SpecIF:isSynonymOf bpmn:Process
- SpecIF:BusinessProcesses SpecIF:isPluralOf SpecIF:BusinessProcess
- SpecIF:BusinessProcesses SpecIF:isPluralOf bpmn:Process
- SpecIF: SpecIF:isNamespace SpecIF:Views
- SpecIF:Views SpecIF:isPluralOf SpecIF:View
- SpecIF: SpecIF:isNamespace SpecIF:BusinessProcesses
- SysML:extends SpecIF:isSynonymOf UML:extends
- SysML: SpecIF:isNamespace SysML:extends
- UML: SpecIF:isNamespace UML:extends
- UML: SpecIF:isNamespace UML:isAggregatedBy
- SysML: SpecIF:isNamespace SysML:isAggregatedBy
- SysML:isAggregatedBy SpecIF:isSynonymOf UML:isAggregatedBy
- DDP: SpecIF:isNamespace DDP:Source
- DDP:Source UML:isSpecializationOf SpecIF:Paragraph
- SpecIF:View SpecIF:hasProperty SpecIF:Diagram
- DDP:Source SpecIF:hasProperty SpecIF:ModelFile
- ArchiMate:Viewpoint SpecIF:hasProperty SpecIF:Diagram
- FMC:Plan SpecIF:hasProperty SpecIF:Diagram
- DDP: SpecIF:isNamespace DDP:definedBy
- DDP:Source SpecIF:isEligibleAsObject DDP:definedBy
